Attribute VB_Name = "Enregistrement_création_Vis"
Sub CATMain()

Dim productDocument1 As ProductDocument
Set productDocument1 = CATIA.ActiveDocument

Dim product1 As Product
Set product1 = productDocument1.Product

product1.PartNumber = "VisCHC"

Set productDocument1 = CATIA.ActiveDocument

productDocument1.SaveAs "C:\Users\Brice\Documents\cours_centrale\S8\maquette numérique\Vis parametrique\test\VisCHC.CATProduct"

Dim products1 As Products
Set products1 = product1.Products

Dim product2 As Product
Set product2 = products1.Item("ecrou_M6S.1")



Dim constraints1 As Constraints
Set constraints1 = product1.Connections("CATIAConstraints")

Dim reference1 As Reference
Set reference1 = product1.CreateReferenceFromName("VisCHC/6*30CHC.1/!VisCHC/6*30CHC.1/")

Dim constraint1 As Constraint
Set constraint1 = constraints1.AddMonoEltCst(catCstTypeReference, reference1)

Set constraints1 = product1.Connections("CATIAConstraints")

Dim reference2 As Reference
Set reference2 = product1.CreateReferenceFromName("VisCHC/rondelle_M6.1/!Axis:(Selection_RSur:(Face:(Brp:(Pad.1;0:(Brp:(Sketch.1;2)));None:();Cf11:());Pad.1_ResultOUT;Z0;G3173))")

Dim reference3 As Reference
Set reference3 = product1.CreateReferenceFromName("VisCHC/6*30CHC.1/!Axis:(Selection_RSur:(Face:(Brp:(Shaft.1;0:(Brp:(Sketch.1;2)));None:();Cf11:());Pocket.1_ResultOUT;Z0;G3173))")

Dim constraint2 As Constraint
Set constraint2 = constraints1.AddBiEltCst(catCstTypeOn, reference2, reference3)

Set constraints1 = product1.Connections("CATIAConstraints")

Set reference3 = product1.CreateReferenceFromName("VisCHC/6*30CHC.1/!Axis:(Selection_RSur:(Face:(Brp:(Shaft.1;0:(Brp:(Sketch.1;2)));None:();Cf11:());Pocket.1_ResultOUT;Z0;G3173))")

Dim reference4 As Reference
Set reference4 = product1.CreateReferenceFromName("VisCHC/rondelle_M6.2/!Axis:(Selection_RSur:(Face:(Brp:(Pad.1;0:(Brp:(Sketch.1;2)));None:();Cf11:());Pad.1_ResultOUT;Z0;G3173))")

Dim constraint3 As Constraint
Set constraint3 = constraints1.AddBiEltCst(catCstTypeOn, reference3, reference4)

Set constraints1 = product1.Connections("CATIAConstraints")

Set reference3 = product1.CreateReferenceFromName("VisCHC/6*30CHC.1/!Axis:(Selection_RSur:(Face:(Brp:(Shaft.1;0:(Brp:(Sketch.1;2)));None:();Cf11:());Pocket.1_ResultOUT;Z0;G3173))")

Dim reference5 As Reference
Set reference5 = product1.CreateReferenceFromName("VisCHC/ecrou_M6S.1/!Axis:(Selection_RSur:(Face:(Brp:(Groove.1;0:(Brp:(Sketch.1;4)));None:();Cf11:());Groove.1_ResultOUT;Z0;G3173))")

Dim constraint4 As Constraint
Set constraint4 = constraints1.AddBiEltCst(catCstTypeOn, reference3, reference5)

Set constraints1 = product1.Connections("CATIAConstraints")

Dim reference6 As Reference
Set reference6 = product1.CreateReferenceFromName("VisCHC/rondelle_M6.1/!Selection_RSur:(Face:(Brp:(Pad.1;2);None:();Cf11:());Pad.1_ResultOUT;Z0;G3173)")

Dim reference7 As Reference
Set reference7 = product1.CreateReferenceFromName("VisCHC/6*30CHC.1/!Selection_RSur:(Face:(Brp:(Shaft.1;0:(Brp:(Sketch.1;3)));None:();Cf11:());Pocket.1_ResultOUT;Z0;G3173)")

Dim constraint5 As Constraint
Set constraint5 = constraints1.AddBiEltCst(catCstTypeSurfContact, reference6, reference7)

Set constraints1 = product1.Connections("CATIAConstraints")

Dim reference8 As Reference
Set reference8 = product1.CreateReferenceFromName("VisCHC/rondelle_M6.2/!Selection_RSur:(Face:(Brp:(Pad.1;1);None:();Cf11:());Pad.1_ResultOUT;Z0;G3173)")

Dim reference9 As Reference
Set reference9 = product1.CreateReferenceFromName("VisCHC/ecrou_M6S.1/!Selection_RSur:(Face:(Brp:((Brp:(Groove.1;0:(Brp:(Sketch.1;1)));Brp:(Pad.1;1)));None:();Cf11:());Groove.1_ResultOUT;Z0;G3173)")

Dim constraint6 As Constraint
Set constraint6 = constraints1.AddBiEltCst(catCstTypeSurfContact, reference8, reference9)

product1.Update

Dim publications1 As Publications
Set publications1 = product1.Publications

Dim long1 As Long
long1 = publications1.Count

Set products1 = product1.Products

Dim long2 As Long
long2 = products1.Count

Dim product5 As Product
Set product5 = products1.Item(1)

Dim publications2 As Publications
Set publications2 = product5.Publications

Dim long3 As Long
long3 = publications2.Count

Dim products2 As Products
Set products2 = product5.Products

Dim long4 As Long
long4 = products2.Count

Set product4 = products1.Item(2)

Dim publications3 As Publications
Set publications3 = product4.Publications

Dim long5 As Long
long5 = publications3.Count

Dim products3 As Products
Set products3 = product4.Products

Dim long6 As Long
long6 = products3.Count

Set product3 = products1.Item(3)

Dim publications4 As Publications
Set publications4 = product3.Publications

Dim long7 As Long
long7 = publications4.Count

Dim products4 As Products
Set products4 = product3.Products

Dim long8 As Long
long8 = products4.Count

Set product2 = products1.Item(4)

Dim publications5 As Publications
Set publications5 = product2.Publications

Dim long9 As Long
long9 = publications5.Count

Dim products5 As Products
Set products5 = product2.Products

Dim long10 As Long
long10 = products5.Count

Set product1 = product1.ReferenceProduct

Dim parameters1 As Parameters
Set parameters1 = product1.Parameters

Dim length1 As Length
Set length1 = parameters1.CreateDimension("", "LENGTH", 0#)

length1.Rename "espacement"

length1.Value = 20#

Set product1 = product1.ReferenceProduct

Set publications1 = product1.Publications

Dim long11 As Long
long11 = publications1.Count

Set products1 = product1.Products

Dim long12 As Long
long12 = products1.Count

Set product5 = products1.Item(1)

Set publications2 = product5.Publications

Dim long13 As Long
long13 = publications2.Count

Set products2 = product5.Products

Dim long14 As Long
long14 = products2.Count

Set product4 = products1.Item(2)

Set publications3 = product4.Publications

Dim long15 As Long
long15 = publications3.Count

Set products3 = product4.Products

Dim long16 As Long
long16 = products3.Count

Set product3 = products1.Item(3)

Set publications4 = product3.Publications

Dim long17 As Long
long17 = publications4.Count

Set products4 = product3.Products

Dim long18 As Long
long18 = products4.Count

Set product2 = products1.Item(4)

Set publications5 = product2.Publications

Dim long19 As Long
long19 = publications5.Count

Set products5 = product2.Products

Dim long20 As Long
long20 = products5.Count

Set publications1 = product1.Publications

Dim long21 As Long
long21 = publications1.Count

Set products1 = product1.Products

Dim long22 As Long
long22 = products1.Count

Set product5 = products1.Item(1)

Set publications2 = product5.Publications

Dim long23 As Long
long23 = publications2.Count

Set products2 = product5.Products

Dim long24 As Long
long24 = products2.Count

Set product4 = products1.Item(2)

Set publications3 = product4.Publications

Dim long25 As Long
long25 = publications3.Count

Set products3 = product4.Products

Dim long26 As Long
long26 = products3.Count

Set product3 = products1.Item(3)

Set publications4 = product3.Publications

Dim long27 As Long
long27 = publications4.Count

Set products4 = product3.Products

Dim long28 As Long
long28 = products4.Count

Set product2 = products1.Item(4)

Set publications5 = product2.Publications

Dim long29 As Long
long29 = publications5.Count

Set products5 = product2.Products

Dim long30 As Long
long30 = products5.Count

Set publications1 = product1.Publications

Dim long31 As Long
long31 = publications1.Count

Set products1 = product1.Products

Dim long32 As Long
long32 = products1.Count

Set product5 = products1.Item(1)

Set publications2 = product5.Publications

Dim long33 As Long
long33 = publications2.Count

Set products2 = product5.Products

Dim long34 As Long
long34 = products2.Count

Set product4 = products1.Item(2)

Set publications3 = product4.Publications

Dim long35 As Long
long35 = publications3.Count

Set products3 = product4.Products

Dim long36 As Long
long36 = products3.Count

Set product3 = products1.Item(3)

Set publications4 = product3.Publications

Dim long37 As Long
long37 = publications4.Count

Set products4 = product3.Products

Dim long38 As Long
long38 = products4.Count

Set product2 = products1.Item(4)

Set publications5 = product2.Publications

Dim long39 As Long
long39 = publications5.Count

Set products5 = product2.Products

Dim long40 As Long
long40 = products5.Count

Set product1 = product1.ReferenceProduct

Set publications1 = product1.Publications

Dim long41 As Long
long41 = publications1.Count

Set products1 = product1.Products

Dim long42 As Long
long42 = products1.Count

Set product5 = products1.Item(1)

Set publications2 = product5.Publications

Dim long43 As Long
long43 = publications2.Count

Set products2 = product5.Products

Dim long44 As Long
long44 = products2.Count

Set product4 = products1.Item(2)

Set publications3 = product4.Publications

Dim long45 As Long
long45 = publications3.Count

Set products3 = product4.Products

Dim long46 As Long
long46 = products3.Count

Set product3 = products1.Item(3)

Set publications4 = product3.Publications

Dim long47 As Long
long47 = publications4.Count

Set products4 = product3.Products

Dim long48 As Long
long48 = products4.Count

Set product2 = products1.Item(4)

Set publications5 = product2.Publications

Dim long49 As Long
long49 = publications5.Count

Set products5 = product2.Products

Dim long50 As Long
long50 = products5.Count

Set publications1 = product1.Publications

Dim long51 As Long
long51 = publications1.Count

Set products1 = product1.Products

Dim long52 As Long
long52 = products1.Count

Set product5 = products1.Item(1)

Set publications2 = product5.Publications

Dim long53 As Long
long53 = publications2.Count

Set products2 = product5.Products

Dim long54 As Long
long54 = products2.Count

Set product4 = products1.Item(2)

Set publications3 = product4.Publications

Dim long55 As Long
long55 = publications3.Count

Set products3 = product4.Products

Dim long56 As Long
long56 = products3.Count

Set product3 = products1.Item(3)

Set publications4 = product3.Publications

Dim long57 As Long
long57 = publications4.Count

Set products4 = product3.Products

Dim long58 As Long
long58 = products4.Count

Set product2 = products1.Item(4)

Set publications5 = product2.Publications

Dim long59 As Long
long59 = publications5.Count

Set products5 = product2.Products

Dim long60 As Long
long60 = products5.Count

Set publications1 = product1.Publications

Dim long61 As Long
long61 = publications1.Count

Set products1 = product1.Products

Dim long62 As Long
long62 = products1.Count

Set product5 = products1.Item(1)

Set publications2 = product5.Publications

Dim long63 As Long
long63 = publications2.Count

Set products2 = product5.Products

Dim long64 As Long
long64 = products2.Count

Set product4 = products1.Item(2)

Set publications3 = product4.Publications

Dim long65 As Long
long65 = publications3.Count

Set products3 = product4.Products

Dim long66 As Long
long66 = products3.Count

Set product3 = products1.Item(3)

Set publications4 = product3.Publications

Dim long67 As Long
long67 = publications4.Count

Set products4 = product3.Products

Dim long68 As Long
long68 = products4.Count

Set product2 = products1.Item(4)

Set publications5 = product2.Publications

Dim long69 As Long
long69 = publications5.Count

Set products5 = product2.Products

Dim long70 As Long
long70 = products5.Count

Dim relations1 As Relations
Set relations1 = product1.Relations

Dim constraint7 As Constraint
Set constraint7 = constraints1.Item("Décalage.7")

Dim length2 As Length
Set length2 = constraint7.Dimension

Dim formula1 As Formula
Set formula1 = relations1.CreateFormula("Formule.2", "", length2, "espacement ")

formula1.Rename "Formule.2"

Set constraints1 = product1.Connections("CATIAConstraints")

Dim reference10 As Reference
Set reference10 = product1.CreateReferenceFromName("VisCHC/rondelle_M6.2/!Selection_RSur:(Face:(Brp:(Pad.1;2);None:();Cf11:());Pad.1_ResultOUT;Z0;G3173)")

Dim reference11 As Reference
Set reference11 = product1.CreateReferenceFromName("VisCHC/rondelle_M6.1/!Selection_RSur:(Face:(Brp:(Pad.1;1);None:();Cf11:());Pad.1_ResultOUT;Z0;G3173)")

Set constraint7 = constraints1.AddBiEltCst(catCstTypeDistance, reference10, reference11)

length2.Value = 20#

constraint7.Orientation = catCstOrientOpposite

product1.Update

Set productDocument1 = CATIA.ActiveDocument

productDocument1.Save

End Sub

Attribute VB_Name = "creationVisV1"
Sub CATMain()

'Création du produit'
Dim document1 As Documents
Set document1 = CATIA.Documents

Dim productDocument1 As Document
Set productDocument1 = Documents1.Add("Product")

Dim AssemblageVis As Product
Set AssemblageVis = productDocument1.Product

Dim Rondelle
Set Rondelle = product1.Products

'Insertion des composant'
'Création des longueur et diamètre de la vis'


'Ajout de la vis

' Dim Vis As Product
' Set Vis = AssemblageVisProducts.AddNewProduct("Vis")

Dim longueur As Integer
Dim diametre As Integer
diametre = 5
longueur = 50

'Dim a As String
'Vis.AddMasterShapeRepresentation "C:\Users\Brice\Documents\cours_centrale\S8\maquette numérique\Vis parametrique\catalogue_vis_ecrou_rondelle\" & diametre & "x" & longueur & ".CATPart"


'Ajout de la rondelle'



Dim localisationRondelle(0)
localisationRondelle(0) = "C:\Users\Brice\Documents\cours_centrale\S8\maquette numérique\Vis parametrique\catalogue_vis_ecrou_rondelle\rondelle_M" & diametre & ".CATPart"
Set Rondelle = AssemblageVis.AddComponentsFromFiles(localisationRondelle, "All")

End Sub

Attribute VB_Name = "enregistrementinsertionvis"
Sub CATMain()

Dim productDocument1 As ProductDocument
Set productDocument1 = CATIA.ActiveDocument

Dim product1 As Product
Set product1 = productDocument1.Product

Dim products1 As Products
Set products1 = product1.Products

Dim arrayOfVariantOfBSTR1(0)
arrayOfVariantOfBSTR1(0) = "C:\Users\Brice\Documents\cours_centrale\S8\maquette numérique\Vis parametrique\catalogue_vis_ecrou_rondelle\2x5.CATPart"
Set products1Variant = products1
products1Variant.AddComponentsFromFiles arrayOfVariantOfBSTR1, "All"

End Sub

Attribute VB_Name = "essai_Vis_contraintepublication"
Sub CATMain()

Dim productDocument1 As ProductDocument
Set productDocument1 = CATIA.ActiveDocument

Dim product1 As Product
Set product1 = productDocument1.Product

Dim products1 As Products
Set products1 = product1.Products

Dim arrayOfVariantOfBSTR1(0)
arrayOfVariantOfBSTR1(0) = "C:\Users\Brice\Documents\cours_centrale\S8\maquette numérique\Vis parametrique\catalogue_vis_ecrou_rondelle\5x30.CATPart"
Set products1Variant = products1
products1Variant.AddComponentsFromFiles arrayOfVariantOfBSTR1, "All"

Dim arrayOfVariantOfBSTR2(0)
arrayOfVariantOfBSTR2(0) = "C:\Users\Brice\Documents\cours_centrale\S8\maquette numérique\Vis parametrique\catalogue_vis_ecrou_rondelle\rondelle_M5.CATPart"
Set products1Variant = products1
products1Variant.AddComponentsFromFiles arrayOfVariantOfBSTR2, "All"

Dim constraints1 As Constraints
Set constraints1 = product1.Connections("CATIAConstraints")

Dim reference1 As Reference
Set reference1 = product1.CreateReferenceFromName("Produit1/5*30.1/!Axis:(Selection_RSur:(Face:(Brp:(Pad.3;0:(Brp:(Sketch.5;1)));None:();Cf11:());Thread.1_ResultOUT;Z0;G3173))")

Dim reference2 As Reference
Set reference2 = product1.CreateReferenceFromName("Produit1/rondelle_M5.1/!Axis:(Selection_RSur:(Face:(Brp:(Pad.1;0:(Brp:(Sketch.1;1)));None:();Cf11:());Pad.1_ResultOUT;Z0;G3173))")

Dim constraint1 As Constraint
Set constraint1 = constraints1.AddBiEltCst(catCstTypeOn, reference1, reference2)

End Sub

Attribute VB_Name = "essai_insertion_vis"
Sub CATMain()

Dim Documents1 As Documents
Set Documents1 = CATIA.Documents

Dim productDocument1 As ProductDocument
Set productDocument1 = Documents1.Add("Product")

Dim product1 As Product
Set product1 = productDocument1.Product

Dim products1 As Products
Set products1 = product1.Products

Dim arrayOfVariantOfBSTR1(0)
arrayOfVariantOfBSTR1(0) = "C:\Program Files (x86)\Dassault Systemes\B19\catalogue_vis_ecrou_rondelle\5x30.CATPart"
Set products1Variant = products1
products1Variant.AddComponentsFromFiles arrayOfVariantOfBSTR1, "CATPart"

Dim arrayOfVariantOfBSTR2(0)
arrayOfVariantOfBSTR2(0) = "C:\Program Files (x86)\Dassault Systemes\B19\catalogue_vis_ecrou_rondelle\rondelle_M5.CATPart"
Set products1Variant = products1
products1Variant.AddComponentsFromFiles arrayOfVariantOfBSTR2, "CATPart"


End Sub

Attribute VB_Name = "essai_publication"
Sub CATMain()

Dim partDocument1 As PartDocument
Set partDocument1 = CATIA.ActiveDocument

Dim part1 As Part
Set part1 = partDocument1.Part

Dim bodies1 As Bodies
Set bodies1 = part1.Bodies

Dim body1 As Body
Set body1 = bodies1.Item("Corps principal")

Dim sketches1 As Sketches
Set sketches1 = body1.Sketches

Dim originElements1 As OriginElements
Set originElements1 = part1.OriginElements

Dim reference1 As Reference
Set reference1 = originElements1.PlaneXY

Dim sketch1 As Sketch
Set sketch1 = sketches1.Add(reference1)

Dim arrayOfVariantOfDouble1(8)
arrayOfVariantOfDouble1(0) = 0#
arrayOfVariantOfDouble1(1) = 0#
arrayOfVariantOfDouble1(2) = 0#
arrayOfVariantOfDouble1(3) = 1#
arrayOfVariantOfDouble1(4) = 0#
arrayOfVariantOfDouble1(5) = 0#
arrayOfVariantOfDouble1(6) = 0#
arrayOfVariantOfDouble1(7) = 1#
arrayOfVariantOfDouble1(8) = 0#
Set sketch1Variant = sketch1
sketch1Variant.SetAbsoluteAxisData arrayOfVariantOfDouble1

part1.InWorkObject = sketch1

Dim factory2D1 As Factory2D
Set factory2D1 = sketch1.OpenEdition()

Dim geometricElements1 As GeometricElements
Set geometricElements1 = sketch1.GeometricElements

Dim axis2D1 As Axis2D
Set axis2D1 = geometricElements1.Item("Repère")

Dim line2D1 As Line2D
Set line2D1 = axis2D1.GetItem("Axe horizontal")

line2D1.ReportName = 1

Dim line2D2 As Line2D
Set line2D2 = axis2D1.GetItem("Axe vertical")

line2D2.ReportName = 2

Dim circle2D1 As Circle2D
Set circle2D1 = factory2D1.CreateClosedCircle(0#, 0#, 25#)

Dim point2D1 As Point2D
Set point2D1 = axis2D1.GetItem("Origine")

circle2D1.CenterPoint = point2D1

circle2D1.ReportName = 3

Dim constraints1 As Constraints
Set constraints1 = sketch1.Constraints

Dim reference2 As Reference
Set reference2 = part1.CreateReferenceFromObject(circle2D1)

Dim constraint1 As Constraint
Set constraint1 = constraints1.AddMonoEltCst(catCstTypeRadius, reference2)

constraint1.Mode = catCstModeDrivingDimension

Dim length1 As Length
Set length1 = constraint1.Dimension

length1.Value = 25#

sketch1.CloseEdition

part1.InWorkObject = sketch1

part1.Update

Dim shapeFactory1 As ShapeFactory
Set shapeFactory1 = part1.ShapeFactory

Dim pad1 As Pad
Set pad1 = shapeFactory1.AddNewPad(sketch1, 20#)

Dim limit1 As Limit
Set limit1 = pad1.FirstLimit

Dim length2 As Length
Set length2 = limit1.Dimension

length2.Value = 40#

part1.Update

Dim product1 As Product
Set product1 = partDocument1.GetItem("Part3")

Dim reference3 As Reference
Set reference3 = product1.CreateReferenceFromName("Part3/!Axis:(Selection_RSur:(Face:(Brp:(Pad.1;0:(Brp:(Sketch.1;3)));None:();Cf11:());Pad.1_ResultOUT;Z0;G3173))")

Dim publications1 As Publications
Set publications1 = product1.Publications

Dim publication1 As Publication
Set publication1 = publications1.Add("Axe")

publications1.SetDirect "Axe", reference3

Dim settingControllers1 As SettingControllers
Set settingControllers1 = CATIA.SettingControllers

Dim visualizationSettingAtt1 As VisualizationSettingAtt
Set visualizationSettingAtt1 = settingControllers1.Item("CATVizVisualizationSettingCtrl")

visualizationSettingAtt1.SaveRepository

End Sub

Attribute VB_Name = "publicationAxeTest"
Sub CATMain()

Dim partDocument1 As PartDocument
Set partDocument1 = CATIA.ActiveDocument

Dim product1 As Product
Set product1 = partDocument1.GetItem("test1")

Dim reference1 As Reference
Set reference1 = product1.CreateReferenceFromName("test1/!Axis:(Selection_RSur:(Face:(Brp:(Pocket.1;0:(Brp:(Sketch.2;1)));None:();Cf11:());Pocket.1_ResultOUT;Z0;G3173))")

Dim publications1 As Publications
Set publications1 = product1.Publications

Dim publication1 As Publication
Set publication1 = publications1.Add("Axe")

publications1.SetDirect "Axe", reference1

Dim reference2 As Reference
Set reference2 = product1.CreateReferenceFromName("test1/!Selection_RSur:(Face:(Brp:(Pad.1;2);None:();Cf11:());Pocket.1_ResultOUT;Z0;G3173)")

Dim publication2 As Publication
Set publication2 = publications1.Add("Face")

publications1.SetDirect "Face", reference2

Dim settingControllers1 As SettingControllers
Set settingControllers1 = CATIA.SettingControllers

Dim visualizationSettingAtt1 As VisualizationSettingAtt
Set visualizationSettingAtt1 = settingControllers1.Item("CATVizVisualizationSettingCtrl")

visualizationSettingAtt1.SaveRepository

End Sub

Attribute VB_Name = "testMesure"
Sub CATMain()

End Sub
