Attribute VB_Name = "FenetreContrainte"
Attribute VB_Base = "0{EB91579B-1FEF-4BFB-8E43-134ABA6D4469}{65EA9F17-82F4-494A-A5F8-CA84B3D554B2}"
Attribute VB_GlobalNameSpace = False
Attribute VB_Creatable = False
Attribute VB_PredeclaredId = True
Attribute VB_Exposed = False
Attribute VB_TemplateDerived = False
Attribute VB_Customizable = False
Private Sub ComboBox1_Change()
    Dim ix As Integer
    ix = 1
    
    While Mid$(prod_Vis.PartNumber, ix, 1) <> "x"
        ix = ix + 1
    Wend
    diametreVis = Mid$(prod_Vis.PartNumber, 1, ix - 1)
    
    If Len(prod_Vis.PartNumber) - ix >= 4 Then
        longueurVis = Mid$(prod_Vis.PartNumber, ix + 1, Len(prod_Vis.PartNumber) - ix - 3)
    Else
        longueurVis = Mid$(prod_Vis.PartNumber, ix + 1, Len(prod_Vis.PartNumber) - ix)
    End If
    
    tableRefDiametreVis = Array(2, 3, 4, 5, 6, 8, 10, 12, 16)
    
    'Efforts fonction des classes
    Dim tableRefClasseEffort(0 To 2) As Variant
    tableRefClasseEffort(0) = Array(829, 2075, 3594, 5886, 8302, 15242, 24275, 35401, 66955) '8.8
    tableRefClasseEffort(1) = Array(1217, 3048, 5279, 8645, 12194, 22388, 35655, 51995, 98340) '10.9
    tableRefClasseEffort(2) = Array(1424, 3567, 6178, 10116, 14269, 26198, 41724, 60845, 115079) '12.9
    'Couples fonction des classes
    Dim tableRefClasseCouple(0 To 2) As Variant
    tableRefClasseCouple(0) = Array(0.339, 1.21, 2.78, 5.5, 9.5, 23, 46, 79, 198) '8.8
    tableRefClasseCouple(1) = Array(0.498, 1.79, 4.09, 8.1, 14, 34, 67, 116, 291) '10.9
    tableRefClasseCouple(2) = Array(0.582, 2.09, 4.79, 9.5, 16.4, 40, 79, 136, 341) '12.9
    
    For i = 0 To 8
        If diametreVis = tableRefDiametreVis(i) Then
            rangVis = i
        End If
    Next i

    Select Case ComboBox1.Value
        Case "8.8"
            LabelEffort.Caption = tableRefClasseEffort(0)(rangVis) & " N"
            LabelCouple.Caption = tableRefClasseCouple(0)(rangVis) & " N.m"
        Case "10.9"
            LabelEffort.Caption = tableRefClasseEffort(1)(rangVis) & " N"
            LabelCouple.Caption = tableRefClasseCouple(1)(rangVis) & " N.m"
        Case "12.9"
            LabelEffort.Caption = tableRefClasseEffort(2)(rangVis) & " N"
            LabelCouple.Caption = tableRefClasseCouple(2)(rangVis) & " N.m"
    End Select
    
End Sub

Private Sub ButtonClose_Click()
    FenetreContrainte.Hide
    FenetrePrincipale.Show

End Sub


Private Sub SelectVis_Click()


    'Masque la fenêtre pour faire la sélection
    FenetreContrainte.Hide
    
    'Déclaration des variables
    Dim USel As Selection
    Dim USelLB
    Dim InputObject(0)
    Dim oStatus
    InputObject(0) = "Part"
    Set USel = CATIA.ActiveDocument.Selection
    Set USelLB = USel
    USel.Clear
    
    'Sélectionner un élément
    oStatus = USelLB.SelectElement2(InputObject, "Sélectionner un élément de la visserie", False)
    If (oStatus = "Cancel") Then
        Exit Sub
    Else
        If Mid$(USelLB.Item(1).LeafProduct.Parent.Parent.PartNumber, 1, 6) = "setVis" Then
            
            Set prod_VisserieSet = USelLB.Item(1).LeafProduct.Parent.Parent
            afficherElementVisserie
        Else
            MsgBox "Attention ! Il ne s'agit pas d'un élément de visserie ou le nom du set de vis (LaVisserie\setVis) n'est plus correct."
        End If
        
        
    End If
    
    'Affichage de la fenetre
    USel.Clear
    FenetreContrainte.Show

End Sub


Sub afficherElementVisserie()

    Dim visProducts As Products
    Set visProducts = prod_VisserieSet.Products
    
    Set prod_Vis = visProducts.Item(1)
    Set prod_Ecrou = visProducts.Item(2)
    
    Labelv.Caption = prod_Vis.PartNumber
    Labele.Caption = prod_Ecrou.PartNumber
    
    If visProducts.Count = 4 Then
        Set prod_Rondelle1 = visProducts.Item(3)
        Set prod_Rondelle2 = visProducts.Item(4)
        Labelr1.Caption = prod_Rondelle1.PartNumber
        Labelr2.Caption = prod_Rondelle2.PartNumber
        
    End If
    
    ' --------------------------------------
    ' Initialisation des éléments dans les combobox
    ' --------------------------------------
    Me.ComboBox1.AddItem "8.8"
    Me.ComboBox1.AddItem "10.9"
    Me.ComboBox1.AddItem "12.9"
    Me.ComboBox1.ListIndex = 0

    
   
    
End Sub

Attribute VB_Name = "FenetreInsertOutil"
Attribute VB_Base = "0{5B3CF7D2-83E4-46F9-AD9C-A670A074F709}{AFF5D674-7AD2-41AE-AE06-B91A6A9D1DB0}"
Attribute VB_GlobalNameSpace = False
Attribute VB_Creatable = False
Attribute VB_PredeclaredId = True
Attribute VB_Exposed = False
Attribute VB_TemplateDerived = False
Attribute VB_Customizable = False

Private Sub SelectVis_Click()

    'Masque la fenêtre pour faire la sélection
    FenetreInsertOutil.Hide
    
    'Déclaration des variables
    Dim USel As Selection
    Dim USelLB
    Dim InputObject(0)
    Dim oStatus
    InputObject(0) = "Part"
    Set USel = CATIA.ActiveDocument.Selection
    Set USelLB = USel
    USel.Clear
    
    'Sélectionner un élément
    oStatus = USelLB.SelectElement2(InputObject, "Sélectionner un élément de la visserie", False)
    If (oStatus = "Cancel") Then
        Exit Sub
    Else
   
        If Mid$(USelLB.Item(1).LeafProduct.Parent.Parent.PartNumber, 1, 6) = "setVis" Then
            Set prod_VisserieSet = USelLB.Item(1).LeafProduct.Parent.Parent
            updateElementVisserie
        Else
            MsgBox "Attention ! Il ne s'agit pas d'un élément de visserie ou le nom du set de vis (LaVisserie\setVis) n'est plus correct."
        End If
        
    End If
    
    'Affichage de la fenetre
    USel.Clear
    FenetreInsertOutil.Show
End Sub


Private Sub CommandButtonFermer_Click()
    'Retour à la fenêtre principale
    FenetreInsertOutil.Hide
    FenetrePrincipale.Show
    
End Sub


Sub updateElementVisserie()

    Dim visProducts As Products
    Set visProducts = prod_VisserieSet.Products
    
    Set prod_Vis = visProducts.Item(1)
    Set prod_Ecrou = visProducts.Item(2)
    Labelv.Caption = prod_Vis.PartNumber
    Labele.Caption = prod_Ecrou.PartNumber
    
    If visProducts.Count = 4 Then
        Set prod_Rondelle1 = visProducts.Item(3)
        Set prod_Rondelle2 = visProducts.Item(4)
        Labelr1.Caption = prod_Rondelle1.PartNumber
        Labelr2.Caption = prod_Rondelle2.PartNumber
    End If
    
    If Right(prod_Vis.PartNumber, 1) = "C" Then
        TeteVis = "CHC"
    Else
        TeteVis = "Hexa"
    End If
    
    diametre = Left(prod_Vis.PartNumber, 2)
    If Right(diametre, 1) = "x" Then
        diametre = Left(diametre, 1)
    End If
    
    
    ' --------------------------------------
    ' Initialisation des éléments dans les combobox
    ' --------------------------------------
    
    If TeteVis = "CHC" Then
        Me.ComboBox1.AddItem "clé mâle côté long"
        Me.ComboBox1.AddItem "clé mâle côté court"
        Me.ComboBox1.ListIndex = 0
        
        Me.ComboBox2.AddItem "clé plate"
        Me.ComboBox2.AddItem "douille"
        Me.ComboBox2.ListIndex = 0
        
    ElseIf diametreVis = "2" Or diametreVis = "3" Then
        Me.ComboBox1.AddItem "clé plate"
        Me.ComboBox1.ListIndex = 0
        
        Me.ComboBox2.AddItem "clé plate"
        Me.ComboBox2.ListIndex = 0
    
    Else
       Me.ComboBox1.AddItem "clé plate"
       Me.ComboBox1.AddItem "douille"
        
       Me.ComboBox2.AddItem "clé plate"
       Me.ComboBox2.AddItem "douille"
    End If
    
    
End Sub

Private Sub CommandButton2_Click()
    ' --------------------------------------
    ' Insertion des outils avec les contraintes
    ' --------------------------------------

    ' --------------------------
    ' Choix des dimensions des outils
    ' --------------------------
    
    Dim visProducts As Products
    Set visProducts = prod_VisserieSet.Products
    
    Set prod_Vis = visProducts.Item(1)
    Set prod_Ecrou = visProducts.Item(2)
    
    
    diametre = Left(prod_Vis.PartNumber, 2)
    If Right(diametre, 1) = "x" Then
        diametre = Left(diametre, 1)
    End If
    diametre = CInt(diametre)
    
    Dim i As Integer
    Dim rangVis As Integer
    
    Dim tableRefDiametreVis As Variant
    Dim tableRefLargeurTeteHexa As Variant
    Dim tableRefLargeurEmpreinteCHC As Variant
    
    tableRefDiametreVis = Array(2, 3, 4, 5, 6, 8, 10, 12, 16)
    tableRefLargeurTeteHexa = Array(4, 5.5, 7, 8, 10, 13, 16, 18, 24)               'Largeur des têtes de vis hexagonales
    tableRefLargeurEmpreinteCHC = Array(1.5, 2.5, 3, 4, 5, 6, 8, 10, 14)            'Largeur des empreintes des vis CHC
    
    For i = 0 To 8
        If diametre = tableRefDiametreVis(i) Then
            rangVis = i
        End If
    Next i
    
    ' --------------------------
    ' Récupération des valeurs des comboBox
    ' --------------------------
    
    choixOutilVis = ComboBox1.Value
    choixOutilEcrou = ComboBox2.Value
    
    
    'Traitement de ces choix
    
    If Right(choixOutilVis, 4) = "ourt" Then
        choixOutilVis = "male"
        cote = "petit"
        largeurCleVis = tableRefLargeurEmpreinteCHC(rangVis)
    ElseIf Right(choixOutilVis, 4) = "long" Then
        choixOutilVis = "male"
        cote = "grand"
        largeurCleVis = tableRefLargeurEmpreinteCHC(rangVis)
    ElseIf Right(choixOutilVis, 4) = "late" Then
        choixOutilVis = "plate"
        largeurCleVis = tableRefLargeurTeteHexa(rangVis)
    Else
        largeurCleVis = tableRefLargeurTeteHexa(rangVis)
    End If
    
    
    If Right(choixOutilEcrou, 4) = "late" Then
        choixOutilEcrou = "plate"
        largeurCleEcrou = tableRefLargeurTeteHexa(rangVis)
    Else
        largeurCleEcrou = tableRefLargeurTeteHexa(rangVis)
    End If
    
    
    ' --------------------------
    ' Environnement actif
    ' --------------------------
    Dim productDocument1 As ProductDocument
    Set productDocument1 = CATIA.ActiveDocument
    
    Dim product1 As Product
    Set product1 = productDocument1.Product
    
    Dim products1 As Products
    Set products1 = product1.Products
    
    Set visserieProduct = CATIA.ActiveDocument.Product.Products.Item("LaVisserie")
    
    Dim visserieProducts As Products
    Set visserieProducts = visserieProduct.Products
    
    ' --------------------------
    ' Nouveau set d'outils
    ' --------------------------
    Dim outilSet As Product
    Set outilSet = visserieProducts.AddNewProduct("setOutil")
    Dim productsOutilSet As Products
    Set productsOutilSet = outilSet.Products
    
    
    ' --------------------------
    ' Récupération des publications de l'outil pour la vis
    ' --------------------------
    'Ouverture de l'outil
    
    nomOutilVis = choixOutilVis & "_" & largeurCleVis
    
    Dim arrayOfVariantOfBSTR1(0)
    arrayOfVariantOfBSTR1(0) = pathCatalogue & "outils\" & nomOutilVis & ".CATPart"
    Set products1Variant = productsOutilSet
    products1Variant.AddComponentsFromFiles arrayOfVariantOfBSTR1, "All"
    'Son product
    Dim oOutilVis As Product
    Set oOutilVis = productsOutilSet.Item(nomOutilVis & ".1")
    
    'Références des publications
    If choixOutilVis = "plate" Or choixOutilVis = "douille" Then
        Set pub = oOutilVis.Publications.Item("Axe")
        Set ref_AxeOutilVis = pub.Valuation
        Set pub = oOutilVis.Publications.Item("Face_inf")
        Set ref_FaceOutilVis = pub.Valuation
    ElseIf cote = "grand" Then
        Set pub = oOutilVis.Publications.Item("Axe_grand")
        Set ref_AxeOutilVis = pub.Valuation
        Set pub = oOutilVis.Publications.Item("Face_grand")
        Set ref_FaceOutilVis = pub.Valuation
    ElseIf cote = "petit" Then
        Set pub = oOutilVis.Publications.Item("Axe_petit")
        Set ref_AxeOutilVis = pub.Valuation
        Set pub = oOutilVis.Publications.Item("Face_petit")
        Set ref_FaceOutilVis = pub.Valuation
    End If

    
    ' --------------------------
    ' Récupération des publications de l'outil pour l'écrou
    ' --------------------------
    'Ouverture de l'outil
    nomOutilEcrou = choixOutilEcrou & "_" & largeurCleEcrou
    arrayOfVariantOfBSTR1(0) = pathCatalogue & "outils\" & nomOutilEcrou & ".CATPart"
    Set products1Variant = productsOutilSet
    products1Variant.AddComponentsFromFiles arrayOfVariantOfBSTR1, "All"
    'Son product
    Dim oOutilEcrou As Product
    Set oOutilEcrou = outilSet.Products.Item(nomOutilEcrou & ".1")
    'Références des publications
    
    Set pub = oOutilEcrou.Publications.Item("Axe")
    Set ref_AxeOutilEcrou = pub.Valuation
    Set pub = oOutilEcrou.Publications.Item("Face_inf")
    Set ref_FaceOutilEcrou = pub.Valuation
       
    ' --------------------------
    ' Récupération des publications de la visserie
    ' --------------------------
    'Pour le vis
    Set pub = prod_Vis.Publications.Item("AxeVis")
    Set ref_Vis_AxeVis = pub.Valuation
    Set pub = prod_Vis.Publications.Item("FaceRondelle")
    Set ref_Vis_FaceRondelle = pub.Valuation
    
    'Pour l'écrou
    Set pub = prod_Ecrou.Publications.Item("AxeVis")
    Set ref_Ecrou_AxeVis = pub.Valuation
    Set pub = prod_Ecrou.Publications.Item("FaceRondelle")
    Set ref_Ecrou_FaceRondelle = pub.Valuation
  
      
    ' --------------------------------------
    ' Création des contraintes ..
    ' --------------------------------------
    'On rend le set de vis flexible
    Dim selSomponent As Selection
    Set selSomponent = CATIA.ActiveDocument.Selection
    Call selSomponent.Clear
    Call selSomponent.Add(visserieProduct.Products.Item(outilSet.Name))
    Call CATIA.StartCommand("Flexible/rigide")
    selSomponent.Clear
    Dim constraints1 As Constraints
    Set constraints1 = product1.Connections("CATIAConstraints")

    
    Dim oConstraintAxe1 As Constraint
    Dim oConstraintAxe2 As Constraint
    Dim oConstraintFaceEcrou As Constraint
    Dim oConstraintFaceVis As Constraint
    
    
    'Contraintes pour l'écrou
    Set oConstraintAxe1 = constraints1.AddBiEltCst(catCstTypeOn, ref_AxeOutilEcrou, ref_Ecrou_AxeVis)
    Set oConstraintFaceEcrou = constraints1.AddBiEltCst(catCstTypeDistance, ref_FaceOutilEcrou, ref_Ecrou_FaceRondelle)
    'oConstraintFaceEcrou.Orientation = catCstOrientOpposite
    oConstraintFaceEcrou.Dimension.Value = 0
    'oConstraintFaceEcrou.Orientation = catCstOrientOpposite


    'Contraintes pour la vis
    Set oConstraintAxe2 = constraints1.AddBiEltCst(catCstTypeOn, ref_AxeOutilVis, ref_Vis_AxeVis)
    Set oConstraintFaceVis = constraints1.AddBiEltCst(catCstTypeDistance, ref_FaceOutilVis, ref_Vis_FaceRondelle)
    'oConstraintFaceVis.Orientation = catCstOrientOpposite
    oConstraintFaceVis.Dimension.Value = 0.3 * diametre
    'oConstraintFaceVis.Orientation = catCstOrientOpposite

    
    update
    
End Sub

Attribute VB_Name = "FenetreInsertion"
Attribute VB_Base = "0{02E49DDE-4C4E-43A8-B006-F7DB057967EF}{372F9AB8-FDC9-4F02-91E9-BE5205A00B5F}"
Attribute VB_GlobalNameSpace = False
Attribute VB_Creatable = False
Attribute VB_PredeclaredId = True
Attribute VB_Exposed = False
Attribute VB_TemplateDerived = False
Attribute VB_Customizable = False


Private Sub CommandButton_SelectAxeTrou_Click()

    ' --------------------------
    ' Selection de publication pour l'axe
    ' --------------------------

    'Masque la fenêtre pour faire la sélection
    FenetreInsertion.Hide
    
    'Déclaration des variables
    Dim USel As Selection
    Dim USelLB
    Dim InputObject(0)
    Dim oStatus
    InputObject(0) = "Publication"
    Set USel = CATIA.ActiveDocument.Selection
    Set USelLB = USel
    USel.Clear
    
    'Sélectionner un élément
    oStatus = USelLB.SelectElement2(InputObject, "Selectionner l'axe du trou", False)
    If (oStatus = "Cancel") Then
        Exit Sub
    Else
        Set axeTrou_ref = USelLB.Item(1).Value.Parent.Item(USelLB.Item(1).Value.Name).Valuation
        LabelSelectAxeTrou.Caption = USelLB.Item(1).Value.Parent.Parent.Name & "_" & USelLB.Item(1).Value.Name
    End If
    
    isAxeSelected = True
    If isAxeSelected * isFaceTeteSelected * isFaceEcrouSelected Then
        obtenirLesMesures
    End If
    
    'Affichage de la fenetre
    USel.Clear
    FenetreInsertion.Show

End Sub

Private Sub CommandButton_SelectFaceTete_Click()

    '---------------------------
    ' Selection de publication pour la face en contact de tête de vis
    ' --------------------------

    'Masque la fenêtre pour faire la sélection
    FenetreInsertion.Hide

    'Déclaration des variables
    Dim USel As Selection
    Dim USelLB
    Dim InputObject(0)
    Dim oStatus
    InputObject(0) = "Publication"
    Set USel = CATIA.ActiveDocument.Selection
    Set USelLB = USel
    USel.Clear
    
    'Sélectionner un élément
    oStatus = USelLB.SelectElement2(InputObject, "Selectionner la face de contact de tête", False)
    If (oStatus = "Cancel") Then
        Exit Sub
    Else
        Set faceContactTete_ref = USelLB.Item(1).Value.Parent.Item(USelLB.Item(1).Value.Name).Valuation
        LabelSelectFaceTete.Caption = USelLB.Item(1).Value.Parent.Parent.Name & "_" & USelLB.Item(1).Value.Name
    End If
    
    isFaceTeteSelected = True
    If isAxeSelected * isFaceTeteSelected * isFaceEcrouSelected Then
        obtenirLesMesures
    End If
    
    'Affichage de la fenetre
    USel.Clear
    FenetreInsertion.Show

End Sub

Private Sub CommandButton_SelectFaceEcrou_Click()

    '---------------------------
    ' Selection de publication pour la face en contact de l'écrou
    ' --------------------------

    'Masque la fenêtre pour faire la sélection
    FenetreInsertion.Hide
    
    'Déclaration des variables
    Dim USel As Selection
    Dim USelLB
    Dim InputObject(0)
    Dim oStatus
    InputObject(0) = "Publication"
    Set USel = CATIA.ActiveDocument.Selection
    Set USelLB = USel
    USel.Clear
    
    'Sélectionner un élément
    oStatus = USelLB.SelectElement2(InputObject, "Selectionner la face de contact écrou", False)
    If (oStatus = "Cancel") Then
        Exit Sub
    Else
        Set faceContactEcrou_ref = USelLB.Item(1).Value.Parent.Item(USelLB.Item(1).Value.Name).Valuation
        LabelSelectFaceEcrou.Caption = USelLB.Item(1).Value.Parent.Parent.Name & "_" & USelLB.Item(1).Value.Name
    End If
    
    isFaceEcrouSelected = True
    If isAxeSelected * isFaceTeteSelected * isFaceEcrouSelected Then
        obtenirLesMesures
    End If
    
    'Affichage de la fenetre
    USel.Clear
    FenetreInsertion.Show

End Sub

Public Sub obtenirLesMesures()
          
    ' --------------------------------------
    ' Récupération des valeurs utiles longueur/rayon ..
    ' --------------------------------------
    Dim TheSPAWorkbench As Workbench
    Set TheSPAWorkbench = CATIA.ActiveDocument.GetWorkbench("SPAWorkbench")
     
    Dim TheMeasurable As Measurable
    Set TheMeasurable = TheSPAWorkbench.GetMeasurable(faceContactTete_ref)
     
    longueurTrou = Round(TheMeasurable.GetMinimumDistance(faceContactEcrou_ref), 10)
    LabelLongueurTrou.Caption = longueurTrou & " mm"
    
    diametreTrou = Round(2 * TheMeasurable.GetMinimumDistance(axeTrou_ref), 10)
    LabelDiametreTrou.Caption = diametreTrou & " mm"
    
    
    CommandButton4.Enabled = True
        
End Sub

Public Sub verificationDesMesures()
    ' --------------------------------------
    ' Récupération des valeurs utiles longueur/rayon ..
    ' --------------------------------------
    Dim TheSPAWorkbench As Workbench
    Set TheSPAWorkbench = CATIA.ActiveDocument.GetWorkbench("SPAWorkbench")
     
    Dim TheMeasurable As Measurable
    Set TheMeasurable = TheSPAWorkbench.GetMeasurable(faceContactTete_ref)
     
    longueurTrou = Round(TheMeasurable.GetMinimumDistance(faceContactEcrou_ref), 10)
    LabelLongueurTrou.Caption = longueurTrou & " mm"
    
    diametreTrou = Round(2 * TheMeasurable.GetMinimumDistance(axeTrou_ref), 10)
    LabelDiametreTrou.Caption = diametreTrou & " mm"
    
    'Vérification du diametre au niveau de la face écrou
    Set TheMeasurable = TheSPAWorkbench.GetMeasurable(faceContactEcrou_ref)
    If diametreTrou = Round(2 * TheMeasurable.GetMinimumDistance(axeTrou_ref), 10) Then
        CommandButton4.Enabled = True
    Else
        
        MsgBox "Trou non régulier ! Vérifiez les éléments séléctionnés, il se peut qu'une des publications soit érronée ou bien que les dimensions du trou soit différentes sur deux éléments de l'assemblage."
        
    End If

End Sub

Public Function derniereVerification()
    validation = True
    ' --------------------------------------
    ' Récupération des valeurs utiles longueur/rayon ..
    ' --------------------------------------
    Dim TheSPAWorkbench As Workbench
    Set TheSPAWorkbench = CATIA.ActiveDocument.GetWorkbench("SPAWorkbench")
     
    Dim TheMeasurable As Measurable
    Set TheMeasurable = TheSPAWorkbench.GetMeasurable(faceContactTete_ref)
     
    longueurTrou = Round(TheMeasurable.GetMinimumDistance(faceContactEcrou_ref), 10)
    LabelLongueurTrou.Caption = longueurTrou & " mm"
    
    diametreTrou = Round(2 * TheMeasurable.GetMinimumDistance(axeTrou_ref), 10)
    LabelDiametreTrou.Caption = diametreTrou & " mm"
    
    'Vérification du diametre au niveau de la face écrou
    Set TheMeasurable = TheSPAWorkbench.GetMeasurable(faceContactEcrou_ref)
    If diametreTrou = Round(2 * TheMeasurable.GetMinimumDistance(axeTrou_ref), 10) Then
        CommandButton4.Enabled = True
    Else
        'Demande à l'utilisateur s'il souhaite forcer le placement
        Dim Response As Integer
        Response = MsgBox("Trou non régulier ! Voulez-vous forcer le placement de la vis ?", vbYesNo)
        If Response = vbYes Then
            validation = True
            
        Else
            validation = False
            
        End If
    End If

End Function


Private Sub CommandButton4_Click()

    verificationDesMesures
    
    ' --------------------------
    ' Récupération des choix des comboBox
    ' --------------------------
    choixEcrou = ComboBoxEcrou.Value
    choixRondelles = ComboBoxRondelles.Value
    choixTeteVis = ComboBoxTeteVis.Value
    
    ' --------------------------
    ' Fonction qui détermine les bons éléments de visserie
    ' --------------------------
    CommandButton5.Enabled = True
    
    'Choix de la vis en fonction des paramètres des comboBox
    choixDeLaVis
    
    If longueurVis = 0 Then
        CommandButton5.Enabled = False
    End If
    
    ' --------------------------
    ' Reference de la vis
    ' --------------------------
    Select Case choixTeteVis
        Case "CHC"
            nom_Vis = diametreVis & "x" & longueurVis & "CHC"
        Case "Hexagonale"
            nom_Vis = diametreVis & "x" & longueurVis
    End Select
    
    ' --------------------------
    ' Reference de l'ecrou
    ' --------------------------
    Select Case choixEcrou
        Case "Standard"
            nom_Ecrou = "ecrou_M" & diametreVis
        Case "Nylstop"
            nom_Ecrou = "ecrou_M" & diametreVis & "_NS"
    End Select
    
    ' --------------------------
    ' Reference des rondelles
    ' --------------------------
    Select Case choixRondelles
        Case "Normales"
            nom_Rondelle1 = "rondelle_M" & diametreVis
            nom_Rondelle2 = "rondelle_M" & diametreVis
        Case "Larges"
            nom_Rondelle1 = "rondelle_M" & diametreVis & "_L"
            nom_Rondelle2 = "rondelle_M" & diametreVis & "_L"
        Case "Sans"
            nom_Rondelle1 = ""
            nom_Rondelle2 = ""
    End Select
    
    ' --------------------------
    ' Affichage de toutes les références choisies
    ' --------------------------
    LabelVisChoix.Caption = nom_Vis
    LabelEcrouChoix.Caption = nom_Ecrou
    LabelRondelleChoix.Caption = nom_Rondelle1

End Sub

Private Sub CommandButton5_Click()

    derniereVerification
    If validation = False Then
        Exit Sub
    End If
    

    ' --------------------------
    ' Environnement actif
    ' --------------------------
    Dim productDocument1 As ProductDocument
    Set productDocument1 = CATIA.ActiveDocument
    
    Dim product1 As Product
    Set product1 = productDocument1.Product
    
    Dim products1 As Products
    Set products1 = product1.Products
    
    Set visserieProduct = CATIA.ActiveDocument.Product.Products.Item("LaVisserie")
    
    Dim visserieProducts As Products
    Set visserieProducts = visserieProduct.Products
    
    ' --------------------------
    ' Nouveau set de vis
    ' --------------------------
    Dim visserieSet As Product
    Set visserieSet = visserieProducts.AddNewProduct("setVis")
    Dim productsVisserieSet As Products
    Set productsVisserieSet = visserieSet.Products
    
    ' --------------------------
    ' Récupération du product de la vis
    ' --------------------------
    'Ouverture de la vis
    Dim arrayOfVariantOfBSTR1(0)
    arrayOfVariantOfBSTR1(0) = pathCatalogue & nom_Vis & ".CATPart"
    Set products1Variant = productsVisserieSet
    products1Variant.AddComponentsFromFiles arrayOfVariantOfBSTR1, "All"
    'Son product
    Dim oVis As Product
    Set oVis = visserieSet.Products.Item(nom_Vis & ".1")
    'Références des publications
    Set pub = oVis.Publications.Item("FaceRondelle")
    Set ref_Vis_FaceRondelle = pub.Valuation
    Set pub = oVis.Publications.Item("AxeVis")
    Set ref_Vis_AxeVis = pub.Valuation
    
    ' --------------------------
    ' Récupération du product de l'ecrou
    ' --------------------------
    'Ouverture de l'ecrou
    arrayOfVariantOfBSTR1(0) = pathCatalogue & nom_Ecrou & ".CATPart"
    Set products1Variant = productsVisserieSet
    products1Variant.AddComponentsFromFiles arrayOfVariantOfBSTR1, "All"
    'Son product
    Dim oEcrou As Product
    Set oEcrou = visserieSet.Products.Item(nom_Ecrou & ".1")
    'Références des publications
    Set pub = oEcrou.Publications.Item("FaceRondelle")
    Set ref_Ecrou_FaceRondelle = pub.Valuation
    Set pub = oEcrou.Publications.Item("AxeVis")
    Set ref_Ecrou_AxeVis = pub.Valuation
    
    ' --------------------------
    ' Récupération du product des rondelles
    ' --------------------------
    'Ouverture des rondelles
    Dim arrayOfVariantOfBSTR
    If nom_Rondelle1 <> "" Then
        arrayOfVariantOfBSTR1(0) = pathCatalogue & nom_Rondelle1 & ".CATPart"
        Set products1Variant = productsVisserieSet
        products1Variant.AddComponentsFromFiles arrayOfVariantOfBSTR1, "All"
        'Son product 1
        Dim oRondelle1 As Product
        Set oRondelle1 = visserieSet.Products.Item(nom_Rondelle1 & ".1")
        'Références des publications 1
        Set pub = oRondelle1.Publications.Item("FaceSup")
        Set ref_Rondelle1_FaceSup = pub.Valuation
        Set pub = oRondelle1.Publications.Item("FaceInf")
        Set ref_Rondelle1_FaceInf = pub.Valuation
        Set pub = oRondelle1.Publications.Item("AxeVis")
        Set ref_Rondelle1_AxeVis = pub.Valuation
        
        arrayOfVariantOfBSTR1(0) = pathCatalogue & nom_Rondelle2 & ".CATPart"
        Set products1Variant = productsVisserieSet
        products1Variant.AddComponentsFromFiles arrayOfVariantOfBSTR1, "All"
        'Son product 2
        Dim oRondelle2 As Product
        Set oRondelle2 = visserieSet.Products.Item(nom_Rondelle2 & ".2")
        'Références des publications 2
        Set pub = oRondelle2.Publications.Item("FaceSup")
        Set ref_Rondelle2_FaceSup = pub.Valuation
        Set pub = oRondelle2.Publications.Item("FaceInf")
        Set ref_Rondelle2_FaceInf = pub.Valuation
        Set pub = oRondelle2.Publications.Item("AxeVis")
        Set ref_Rondelle2_AxeVis = pub.Valuation
    End If
    
    ' --------------------------------------
    ' Création des contraintes ..
    ' --------------------------------------
    'On rend le set de vis flexible
    Dim selSomponent As Selection
    Set selSomponent = CATIA.ActiveDocument.Selection
    Call selSomponent.Clear
    Call selSomponent.Add(visserieProduct.Products.Item(visserieSet.Name))
    Call CATIA.StartCommand("Flexible/rigide")
    selSomponent.Clear

    Dim constraints1 As Constraints
    Set constraints1 = product1.Connections("CATIAConstraints")
    
    Dim oConstraintAxe1 As Constraint
    Dim oConstraintAxe2 As Constraint
    Dim oConstraintAxe3 As Constraint
    Dim oConstraintAxe4 As Constraint
    Dim oConstraintcontact1 As Constraint
    Dim oConstraintcontact2 As Constraint
    Dim oConstraintcontact3 As Constraint
    Dim oConstraintcontact4 As Constraint
    Dim sel As Selection
    
    'Cas avec rondelles
    If nom_Rondelle1 <> "" Then
        'Contraintes de coincidence
        Set oConstraintAxe1 = constraints1.AddBiEltCst(catCstTypeOn, ref_Vis_AxeVis, axeTrou_ref)
        Set oConstraintAxe2 = constraints1.AddBiEltCst(catCstTypeOn, ref_Ecrou_AxeVis, axeTrou_ref)
        Set oConstraintAxe3 = constraints1.AddBiEltCst(catCstTypeOn, ref_Rondelle1_AxeVis, axeTrou_ref)
        Set oConstraintAxe4 = constraints1.AddBiEltCst(catCstTypeOn, ref_Rondelle2_AxeVis, axeTrou_ref)
        'Contraintes contact surfacique
        Set oConstraintcontact1 = constraints1.AddBiEltCst(catCstTypeSurfContact, ref_Vis_FaceRondelle, ref_Rondelle1_FaceSup)
        Set oConstraintcontact2 = constraints1.AddBiEltCst(catCstTypeSurfContact, ref_Rondelle1_FaceInf, faceContactTete_ref)
        Set oConstraintcontact3 = constraints1.AddBiEltCst(catCstTypeSurfContact, faceContactEcrou_ref, ref_Rondelle2_FaceSup)
        Set oConstraintcontact4 = constraints1.AddBiEltCst(catCstTypeSurfContact, ref_Rondelle2_FaceInf, ref_Ecrou_FaceRondelle)
        'Regroupe les contraintes dans un groupe
        Set sel = CATIA.ActiveDocument.Selection
        Call sel.Clear
        Call sel.Add(constraints1.Item(oConstraintAxe1.Name))
        Call sel.Add(constraints1.Item(oConstraintAxe2.Name))
        Call sel.Add(constraints1.Item(oConstraintAxe3.Name))
        Call sel.Add(constraints1.Item(oConstraintAxe4.Name))
        Call sel.Add(constraints1.Item(oConstraintcontact1.Name))
        Call sel.Add(constraints1.Item(oConstraintcontact2.Name))
        Call sel.Add(constraints1.Item(oConstraintcontact3.Name))
        Call sel.Add(constraints1.Item(oConstraintcontact4.Name))
        Call CATIA.StartCommand("Regrouper dans un nouveau groupe")
        sel.Clear
        
    'Cas sans rondelles
    Else
        'Contraintes de coincidence
        Set oConstraintAxe1 = constraints1.AddBiEltCst(catCstTypeOn, ref_Vis_AxeVis, axeTrou_ref)
        Set oConstraintAxe2 = constraints1.AddBiEltCst(catCstTypeOn, ref_Ecrou_AxeVis, axeTrou_ref)
        'Contraintes contact surfacique
        Set oConstraintcontact1 = constraints1.AddBiEltCst(catCstTypeSurfContact, ref_Vis_FaceRondelle, faceContactTete_ref)
        Set oConstraintcontact2 = constraints1.AddBiEltCst(catCstTypeSurfContact, faceContactEcrou_ref, ref_Ecrou_FaceRondelle)
        'Regroupe les contraintes dans un groupe
        Set sel = CATIA.ActiveDocument.Selection
        Call sel.Clear
        Call sel.Add(constraints1.Item(oConstraintAxe1.Name))
        Call sel.Add(constraints1.Item(oConstraintAxe2.Name))
        Call sel.Add(constraints1.Item(oConstraintcontact1.Name))
        Call sel.Add(constraints1.Item(oConstraintcontact2.Name))
        Call CATIA.StartCommand("Regrouper dans un nouveau groupe")
        sel.Clear
    
    End If
    
    ' --------------------------------------
    ' Mise àjour du Product
    ' --------------------------------------
    CommandButton5.Enabled = False
    
    update

End Sub


Private Sub CommandButton6_Click()

    FenetreInsertion.Hide
    FenetrePrincipale.Show

End Sub



Private Sub UserForm_Initialize()
    
    LabelSelectAxeTrou.Caption = "..."
    LabelSelectFaceTete.Caption = "..."
    LabelSelectFaceEcrou.Caption = "..."
    isAxeSelected = False
    isFaceTeteSelected = False
    isFaceEcrouSelected = False
    ' --------------------------------------
    ' Initialisation des éléments dans les combobox
    ' --------------------------------------
    Me.ComboBoxTeteVis.AddItem "CHC"
    Me.ComboBoxTeteVis.AddItem "Hexagonale"
    Me.ComboBoxTeteVis.ListIndex = 0
    
    Me.ComboBoxEcrou.AddItem "Nylstop"
    Me.ComboBoxEcrou.AddItem "Standard"
    Me.ComboBoxEcrou.ListIndex = 0
    
    Me.ComboBoxRondelles.AddItem "Normales"
    Me.ComboBoxRondelles.AddItem "Larges"
    Me.ComboBoxRondelles.AddItem "Sans"
    Me.ComboBoxRondelles.ListIndex = 0

End Sub

Attribute VB_Name = "FenetreModif"
Attribute VB_Base = "0{A00DAB2E-6702-4A3E-AD06-4FFDD05FC2D2}{9BA19448-B410-4D1C-9988-094B3F1DE8B9}"
Attribute VB_GlobalNameSpace = False
Attribute VB_Creatable = False
Attribute VB_PredeclaredId = True
Attribute VB_Exposed = False
Attribute VB_TemplateDerived = False
Attribute VB_Customizable = False
Private Sub ComboBox1_Change()

    Select Case ComboBox1.Value
        Case "CHC"
            nom_Vis = diametreVis & "x" & longueurVis & "CHC"
        Case "Hexagonale"
            nom_Vis = diametreVis & "x" & longueurVis
    End Select
    
    Set prod_Vis = prod_VisserieSet.Products.ReplaceComponent( _
          prod_Vis, _
          "C:\CATIA\Vis parametrique\catalogue_vis_ecrou_rondelle\" & nom_Vis & ".CATPart", _
          True)
          
    update
    updateElementVisserie
    
End Sub

Private Sub ComboBox2_Change()

    Select Case ComboBox2.Value
        Case "Standard"
            nom_Ecrou = "ecrou_M" & diametreVis
        Case "Nylstop"
            nom_Ecrou = "ecrou_M" & diametreVis & "_NS"
    End Select
    
    Set prod_Ecrou = prod_VisserieSet.Products.ReplaceComponent( _
          prod_Ecrou, _
          "C:\CATIA\Vis parametrique\catalogue_vis_ecrou_rondelle\" & nom_Ecrou & ".CATPart", _
          True)
          
    update
    updateElementVisserie
    
End Sub

Private Sub ComboBox3_Change()

    Select Case ComboBox3.Value
        Case "Normales"
            nom_Rondelle1 = "rondelle_M" & diametreVis
            nom_Rondelle2 = "rondelle_M" & diametreVis
        Case "Larges"
            nom_Rondelle1 = "rondelle_M" & diametreVis & "_L"
            nom_Rondelle2 = "rondelle_M" & diametreVis & "_L"
    End Select
    
     Set prod_Rondelle1 = prod_VisserieSet.Products.ReplaceComponent( _
          prod_Rondelle1, _
          "C:\CATIA\Vis parametrique\catalogue_vis_ecrou_rondelle\" & nom_Rondelle1 & ".CATPart", _
          True)
    
    Set prod_Rondelle2 = prod_VisserieSet.Products.ReplaceComponent( _
          prod_Rondelle2, _
          "C:\CATIA\Vis parametrique\catalogue_vis_ecrou_rondelle\" & nom_Rondelle2 & ".CATPart", _
          True)
          
    update
    updateElementVisserie
    
End Sub

Private Sub CommandButton1_Click()
    
    'Masque la fenêtre pour faire la sélection
    FenetreModif.Hide
    
    'Déclaration des variables
    Dim USel As Selection
    Dim USelLB
    Dim InputObject(0)
    Dim oStatus
    InputObject(0) = "Part"
    Set USel = CATIA.ActiveDocument.Selection
    Set USelLB = USel
    USel.Clear
    
    'Sélectionner un élément
    oStatus = USelLB.SelectElement2(InputObject, "Sélectionner un élément de la visserie", False)
    If (oStatus = "Cancel") Then
        Exit Sub
    Else
    
        If Mid$(USelLB.Item(1).LeafProduct.Parent.Parent.PartNumber, 1, 6) = "setVis" Then
            Set prod_VisserieSet = USelLB.Item(1).LeafProduct.Parent.Parent
            updateElementVisserie
        Else
            MsgBox "Attention ! Il ne s'agit pas d'un élément de visserie ou le nom du set de vis (LaVisserie\setVis) n'est plus correct."
        End If
        
    End If
    
    'Affichage de la fenetre
    USel.Clear
    FenetreModif.Show

End Sub


Sub updateElementVisserie()

    Dim visProducts As Products
    Set visProducts = prod_VisserieSet.Products
    
    Set prod_Vis = visProducts.Item(1)
    Set prod_Ecrou = visProducts.Item(2)
    
    
    Label1.Caption = prod_Vis.PartNumber
    Label2.Caption = prod_Ecrou.PartNumber
    ComboBox1.Visible = True
    ComboBox2.Visible = True
    
    
    
    Dim ix As Integer
    ix = 1
    
    While Mid$(prod_Vis.PartNumber, ix, 1) <> "x"
        ix = ix + 1
    Wend
    diametreVis = Mid$(prod_Vis.PartNumber, 1, ix - 1)
    If Len(prod_Vis.PartNumber) - ix >= 4 Then
        longueurVis = Mid$(prod_Vis.PartNumber, ix + 1, Len(prod_Vis.PartNumber) - ix - 3)
    Else
        longueurVis = Mid$(prod_Vis.PartNumber, ix + 1, Len(prod_Vis.PartNumber) - ix)
    End If
        
    
    If Mid$(prod_Vis.PartNumber, Len(prod_Vis.PartNumber), 1) = "C" Then
        Me.ComboBox1.ListIndex = 0
    Else
        Me.ComboBox1.ListIndex = 1
    End If
    
    If Mid$(prod_Ecrou.PartNumber, Len(prod_Ecrou.PartNumber), 1) = "S" Then
        Me.ComboBox2.ListIndex = 0
    Else
        Me.ComboBox2.ListIndex = 1
    End If
    
    If visProducts.Count = 4 Then
        Set prod_Rondelle1 = visProducts.Item(3)
        Set prod_Rondelle2 = visProducts.Item(4)
        Label3.Caption = prod_Rondelle1.PartNumber
        ComboBox3.Visible = True
        
        If Mid$(prod_Rondelle1.PartNumber, Len(prod_Rondelle1.PartNumber), 1) = "L" Then
            Me.ComboBox3.ListIndex = 1
        Else
            Me.ComboBox3.ListIndex = 0
        End If
        
    End If

End Sub


Private Sub CommandButton6_Click()
    FenetreModif.Hide
    FenetrePrincipale.Show

End Sub


Private Sub UserForm_Initialize()

    ' --------------------------------------
    ' Initialisation des éléments dans les combobox
    ' --------------------------------------
    Me.ComboBox1.AddItem "CHC"
    Me.ComboBox1.AddItem "Hexagonale"
    
    Me.ComboBox2.AddItem "Nylstop"
    Me.ComboBox2.AddItem "Standard"
    
    Me.ComboBox3.AddItem "Normales"
    Me.ComboBox3.AddItem "Larges"

End Sub

Attribute VB_Name = "FenetrePrincipale"
Attribute VB_Base = "0{6EF69AF3-34A7-47FC-AA0A-7D7B7C48F8FD}{058B8157-ACD8-43ED-A6D7-9FB1178B0DD3}"
Attribute VB_GlobalNameSpace = False
Attribute VB_Creatable = False
Attribute VB_PredeclaredId = True
Attribute VB_Exposed = False
Attribute VB_TemplateDerived = False
Attribute VB_Customizable = False

Private Sub CommandButtonResistance_Click()
    ' --------------------------
    ' Ouverture nouvelle fenetre Resistance
    ' --------------------------
    FenetrePrincipale.Hide
    FenetreContrainte.Show

End Sub

Private Sub CommandButtonInserer_Click()
    ' --------------------------
    ' Ouverture nouvelle fenetre Insertion
    ' --------------------------
    FenetrePrincipale.Hide
    FenetreInsertion.Show

End Sub

Private Sub CommandButtonModifier_Click()
    ' --------------------------
    ' Ouverture nouvelle fenetre Modification
    ' --------------------------
    FenetrePrincipale.Hide
    FenetreModif.Show

End Sub

Private Sub CommandButtonOutil_Click()
    ' --------------------------
    ' Ouverture nouvelle fenetre d'insertion des outils
    ' --------------------------
    
    FenetrePrincipale.Hide
    FenetreInsertOutil.Show
    
End Sub

Private Sub CommandButtonSupprimer_Click()
    ' --------------------------
    ' Ouverture nouvelle fenetre Suppression
    ' --------------------------
    FenetrePrincipale.Hide
    FenetreSuppr.Show

End Sub

Private Sub UserForm_Click()

End Sub

Attribute VB_Name = "FenetreSuppr"
Attribute VB_Base = "0{757D2832-9E11-46C9-8F58-89D339522AF1}{90CC6DD7-E473-422C-8634-E97B6A163509}"
Attribute VB_GlobalNameSpace = False
Attribute VB_Creatable = False
Attribute VB_PredeclaredId = True
Attribute VB_Exposed = False
Attribute VB_TemplateDerived = False
Attribute VB_Customizable = False
Private Sub CommandButton1_Click()

    ' --------------------------
    ' Environnement actif
    ' --------------------------
    Dim productDocument1 As ProductDocument
    Set productDocument1 = CATIA.ActiveDocument
    
    Dim product1 As Product
    Set product1 = productDocument1.Product
    
    Dim oConstraintsCol As Constraints
    Set oConstraintsCol = product1.Connections("CATIAConstraints")
    
    Dim selDel As Selection
    Set selDel = CATIA.ActiveDocument.Selection

    selDel.Clear
    selDel.Add prod_VisserieSet
    
    selDel.Delete
    
    update
    
    Me.CommandButton1.Enabled = False

End Sub

Private Sub ButtonClose_Click()

    FenetreSuppr.Hide
    FenetrePrincipale.Show
    
End Sub

Private Sub SelectVis_Click()

    'Masque la fenêtre pour faire la sélection
    FenetreSuppr.Hide
    
    'Déclaration des variables
    Dim USel As Selection
    Dim USelLB
    Dim InputObject(0)
    Dim oStatus
    InputObject(0) = "Part"
    Set USel = CATIA.ActiveDocument.Selection
    Set USelLB = USel
    USel.Clear
    
    'Sélectionner un élément
    oStatus = USelLB.SelectElement2(InputObject, "Sélectionner un élément de la visserie", False)
    If (oStatus = "Cancel") Then
        Exit Sub
    Else
        If Mid$(USelLB.Item(1).LeafProduct.Parent.Parent.PartNumber, 1, 6) = "setVis" Then
            
            Set prod_VisserieSet = USelLB.Item(1).LeafProduct.Parent.Parent
            afficherElementVisserie
        Else
            MsgBox "Attention ! Il ne s'agit pas d'un élément de visserie ou le nom du set de vis (LaVisserie\setVis) n'est plus correct."
        End If
        
        
    End If
    
    'Affichage de la fenetre
    USel.Clear
    FenetreSuppr.Show

End Sub


Sub afficherElementVisserie()

    Dim visProducts As Products
    Set visProducts = prod_VisserieSet.Products
    
    Set prod_Vis = visProducts.Item(1)
    Set prod_Ecrou = visProducts.Item(2)
    
    Label1.Caption = prod_Vis.PartNumber
    Label2.Caption = prod_Ecrou.PartNumber
    
    If visProducts.Count = 4 Then
        Set prod_Rondelle1 = visProducts.Item(3)
        Set prod_Rondelle2 = visProducts.Item(4)
        Label3.Caption = prod_Rondelle1.PartNumber
        Label4.Caption = prod_Rondelle2.PartNumber
        
    End If
    
    Me.CommandButton1.Enabled = True

End Sub

Attribute VB_Name = "Module1"

Sub CATMain()

    ' --------------------------
    ' Environnement actif
    ' --------------------------
    Dim productDocument1 As ProductDocument
    Set productDocument1 = CATIA.ActiveDocument
    
    Dim product1 As Product
    Set product1 = productDocument1.Product
    
    Dim products1 As Products
    Set products1 = product1.Products
    
    ' --------------------------
    ' Recherche de la visserie et création si elle n'existe pas
    ' --------------------------
    Dim objSel As Selection
    Set objSel = CATIA.ActiveDocument.Selection
    objSel.Search ("Name=LaVisserie*,all")
    objcount = objSel.Count
    
    Dim visserieProduct As Product
    
    'Création de la visserie et recherche du catalogue
    If objcount = 0 Then
        MsgBox "Première utilisation --> Création de la visserie"
        Set visserieProduct = products1.AddNewProduct("LaVisserie")
        visserieProduct.Name = "LaVisserie"
        
        'Ouverture du FileBrowser
        Const WINDOW_HANDLE = 0
        Const NO_OPTIONS = &H1
        Dim objShellApp
        Dim objFolder
        Dim objFldrItem
        Dim objPath
        
        Set objShellApp = CreateObject("Shell.Application")
        Set objFolder = objShellApp.BrowseForFolder(WINDOW_HANDLE, strTitle, NO_OPTIONS)
        
        If IobjFolder = Null Then
            WScript.Echo "You choose to cancel. This will stop this script."
            WScript.Quit
        Else
            Set objFldrItem = objFolder.Self
            objPath = objFldrItem.Path
            
            visserieProduct.DescriptionRef = objPath & "\"
            
            Set objShellApp = Nothing
            Set objFolder = Nothing
            Set objFldrItem = Nothing
            
        End If
    
    'La visserie existe déjà
    Else
        Set visserieProduct = CATIA.ActiveDocument.Product.Products.Item("LaVisserie")
    End If
    
    'Récupération du chemin d'acces du catalogue
    pathCatalogue = visserieProduct.DescriptionRef
        
    'Affichage de la fenetre
    FenetrePrincipale.Show

End Sub

Public Sub update()

    ' --------------------------
    ' Mise à jour de tout le produit
    ' --------------------------
    Dim productDocument1 As ProductDocument
    Set productDocument1 = CATIA.ActiveDocument
    
    Dim product1 As Product
    Set product1 = productDocument1.Product
    
    product1.update

End Sub


Public Sub choixDeLaVis()

    Dim i As Integer
    Dim rangVis As Integer
    
    ' --------------------------
    ' Initialisation des tables de conversion
    ' --------------------------
    Dim tableRefDiametreVis As Variant
    Dim tableRefPasVis As Variant
    Dim tableRefHauteurEcrou As Variant
    Dim tableRefHauteurEcrouNilstop As Variant
    Dim tableRefEpaisseurRondelle As Variant
    Dim tableRefEpaisseurRondelleLarge As Variant
    
    tableRefDiametreVis = Array(2, 3, 4, 5, 6, 8, 10, 12, 16)                       'Diamètre
    tableRefPasVis = Array(0.4, 0.5, 0.7, 0.8, 1, 1.25, 1.5, 1.75, 2)               'Pas de vis
    tableRefHauteurEcrou = Array(1.6, 2.4, 3.2, 4.7, 5.2, 6.8, 8.4, 10.8, 14.8)     'Epaisseur écrou standard
    tableRefHauteurEcrouNilstop = Array(1.6, 4.5, 6, 6.8, 8, 9.5, 11.9, 14.9, 19.1) 'Epaisseur écrou Nilstop
    tableRefEpaisseurRondelle = Array(0.3, 0.5, 0.8, 1, 1.6, 1.6, 2, 2.5, 3)        'Epaisseur rondelle standard
    tableRefEpaisseurRondelleLarge = Array(0.5, 0.8, 1, 1.2, 1.6, 2, 2.5, 3, 3)     'Epaisseur rondelle large
    
    
    'Longueur des vis fonction des diamètres
    Dim tableRefLongueurVis(0 To 8) As Variant
    tableRefLongueurVis(0) = Array(4, 5, 6, 8, 10, 12, 16)
    tableRefLongueurVis(1) = Array(5, 6, 8, 10, 12, 16, 20, 25, 30)
    tableRefLongueurVis(2) = Array(8, 10, 12, 16, 20, 25, 30, 35, 40)
    tableRefLongueurVis(3) = Array(10, 12, 16, 20, 25, 30, 35, 40, 45, 50)
    tableRefLongueurVis(4) = Array(12, 16, 20, 25, 30, 35, 40, 45, 50, 55, 60)
    tableRefLongueurVis(5) = Array(16, 20, 25, 30, 35, 40, 45, 50, 55, 60, 65, 70, 75, 80, 100)
    tableRefLongueurVis(6) = Array(20, 25, 30, 35, 40, 45, 50, 55, 60, 65, 70, 75, 80, 90, 100)
    tableRefLongueurVis(7) = Array(25, 30, 35, 40, 45, 50, 55, 60, 65, 70, 75, 80, 90, 100, 110, 120)
    tableRefLongueurVis(8) = Array(30, 35, 40, 45, 50, 55, 60, 65, 70, 75, 80, 90, 100, 110, 120, 130, 140, 150, 160, 170, 180, 190, 200)
    
    ' --------------------------
    ' Choix du diametre de vis
    ' --------------------------
    If diametreTrou < tableRefDiametreVis(0) Then
        MsgBox "Attention ! Aucune vis suffisamment petite pour ce trou."
        Exit Sub
    End If
    
    For i = 0 To 8
        If tableRefDiametreVis(i) <= diametreTrou Then
            diametreVis = tableRefDiametreVis(i)
            rangVis = i
        Else
            If diametreVis = diametreTrou Then
                MsgBox "Attention ! Contact serré"
            End If
            Exit For
        End If
    Next i
    
    If diametreVis = tableRefDiametreVis(UBound(tableRefDiametreVis)) Then
        MsgBox "Attention ! Risque de flottement. La vis choisie pour ce trou est la plus large du catalogue."
    End If
    
    ' --------------------------
    ' Pas de vis
    ' --------------------------
    pasVis = tableRefPasVis(rangVis)
    
    ' --------------------------
    ' Ecrou
    ' --------------------------
    Select Case choixEcrou
        Case "Standard"
            hauteurEcrou = tableRefHauteurEcrou(rangVis)
        Case "Nylstop"
            hauteurEcrou = tableRefHauteurEcrouNilstop(rangVis)
    End Select
    
    ' --------------------------
    ' Rondelles
    ' --------------------------
    Select Case choixRondelles
        Case "Normales"
            epaisseurRondelles = 2 * tableRefEpaisseurRondelle(rangVis)
        Case "Larges"
            epaisseurRondelles = 2 * tableRefEpaisseurRondelleLarge(rangVis)
        Case "Sans"
            epaisseurRondelles = 0
    End Select
    
    ' --------------------------
    ' Choix de la vis
    ' --------------------------
    Dim longueurMinimale As Double
    longueurMinimale = longueurTrou + epaisseurRondelles + hauteurEcrou + 2 * pasVis
    longueurVis = 0
    For i = 0 To UBound(tableRefLongueurVis(rangVis))
        If tableRefLongueurVis(rangVis)(i) >= longueurMinimale Then
            longueurVis = tableRefLongueurVis(rangVis)(i)
            Exit For
        End If
    Next i
    
    If longueurVis = 0 Then
        MsgBox "Attention ! Aucune vis suffisamment longue pour ce trou."
        Exit Sub
    End If

End Sub

Attribute VB_Name = "ModuleVariables"
' --------------------------------------
' Création des variables globales
' --------------------------------------

Public pathCatalogue As String

'Variables de l'emplacement de la vis
Public axeTrou_ref
Public faceContactTete_ref
Public faceContactEcrou_ref

Public isAxeSelected As Boolean
Public isFaceTeteSelected As Boolean
Public isFaceEcrouSelected As Boolean

Public longueurTrou As Double
Public diametreTrou As Double

'Variables de visserie
Public choixEcrou As String
Public choixRondelles As String
Public choixTeteVis As String

Public diametreVis As Double
Public pasVis As Double
Public hauteurEcrou As Double
Public epaisseurRondelles As Double
Public longueurVis As Double

Public nom_Vis As String
Public nom_Rondelle1 As String
Public nom_Rondelle2 As String
Public nom_Ecrou As String

Public prod_VisserieSet As Product
Public prod_Vis As Product
Public prod_Rondelle1 As Product
Public prod_Rondelle2 As Product
Public prod_Ecrou As Product

Public validation As Boolean
