Attribute VB_Name = "ModulePath"
Sub CATMain()

Dim productDocument1 As ProductDocument
Set productDocument1 = CATIA.ActiveDocument

Dim product1 As Product
Set product1 = productDocument1.GetItem("LaVisserie")

product1.DescriptionRef = "Bonjour, je m'appelle Jules"

End Sub

Attribute VB_Name = "test_contrainte"
Sub CATMain()

Dim productDocument1 As ProductDocument
Set productDocument1 = CATIA.ActiveDocument

Dim selection1 As Selection
Set selection1 = productDocument1.Selection

selection1.Clear

Dim product1 As Product
Set product1 = productDocument1.Product

Dim products1 As Products
Set products1 = product1.Products

Dim product2 As Product
Set product2 = products1.Item("LaVisserie")

Dim products2 As Products
Set products2 = product2.Products

Dim product3 As Product
Set product3 = products2.Item("setOutil.7")

selection1.Add product3

selection1.Delete

Set product2 = products1.Item("LaVisserie")

Set products2 = product2.Products

Set Nothing1 = products2.Item("setOutil.7")

Set product2 = products1.Item("LaVisserie")

Set products2 = product2.Products

Set Nothing1 = products2.Item("setOutil.7")

Set product2 = products1.Item("LaVisserie")

Set products2 = product2.Products

Dim product4 As Product
Set product4 = products2.Item("setVis.2")

Dim products3 As Products
Set products3 = product4.Products

Dim product5 As Product
Set product5 = products3.Item("2x16CHC.1")

Dim products4 As Products
Set products4 = product5.Products

Set product2 = products1.Item("LaVisserie")

Set products2 = product2.Products

Set Nothing1 = products2.Item("setOutil.7")

Set product2 = products1.Item("LaVisserie")

Set products2 = product2.Products

Set Nothing1 = products2.Item("setOutil.7")

Set product2 = products1.Item("LaVisserie")

Set products2 = product2.Products

Set Nothing1 = products2.Item("setOutil.7")

Set product2 = products1.Item("LaVisserie")

Set products2 = product2.Products

Set Nothing1 = products2.Item("setOutil.7")

Set product2 = products1.Item("LaVisserie")

Set products2 = product2.Products

Set Nothing1 = products2.Item("setOutil.7")

Set productDocument1 = CATIA.ActiveDocument

Dim selection2 As Selection
Set selection2 = productDocument1.Selection

selection2.Clear

Dim constraints1 As Constraints
Set constraints1 = product1.Connections("CATIAConstraints")

Dim constraint1 As Constraint
Set constraint1 = constraints1.Item("Coïncidence.40")

selection2.Add constraint1

selection2.Delete

Set productDocument1 = CATIA.ActiveDocument

Set product1 = productDocument1.Product

Set products1 = product1.Products

Set productDocument1 = CATIA.ActiveDocument

Dim selection3 As Selection
Set selection3 = productDocument1.Selection

selection3.Search "Name=LaVisserie*,all"

Dim long1 As Long
long1 = selection3.Count

Set productDocument1 = CATIA.ActiveDocument

Set product1 = productDocument1.Product

Set products1 = product1.Products

Set product2 = products1.Item("LaVisserie")

Dim bSTR1 As String
bSTR1 = product2.DescriptionRef

Set productDocument1 = CATIA.ActiveDocument

Set selection3 = productDocument1.Selection

selection3.Clear

Dim arrayOfVariantOfBSTR1(0)
arrayOfVariantOfBSTR1(0) = "Part"
Dim bSTR2 As String
Set selection3Variant = selection3
bSTR2 = selection3Variant.SelectElement2(arrayOfVariantOfBSTR1, "Sélectionner un élément de la visserie", False)

Dim selectedElement1 As SelectedElement
Set selectedElement1 = selection3.Item(1)

Set product5 = selectedElement1.LeafProduct

Set products3 = product5.Parent

Set product4 = products3.Parent

Dim bSTR3 As String
bSTR3 = product4.PartNumber

Dim selectedElement2 As SelectedElement
Set selectedElement2 = selection3.Item(1)

Set product5 = selectedElement2.LeafProduct

Set products3 = product5.Parent

Set product4 = products3.Parent

Set products3 = product4.Products

Set product5 = products3.Item(1)

Dim product6 As Product
Set product6 = products3.Item(2)

Dim bSTR4 As String
bSTR4 = product5.PartNumber

Dim bSTR5 As String
bSTR5 = product5.PartNumber

selection3.Clear

Set products3 = product4.Products

Set product5 = products3.Item(1)

Set product6 = products3.Item(2)

Dim bSTR6 As String
bSTR6 = product5.PartNumber

Set productDocument1 = CATIA.ActiveDocument

Set product1 = productDocument1.Product

Set products1 = product1.Products

Set productDocument1 = CATIA.ActiveDocument

Set product1 = productDocument1.Product

Set products1 = product1.Products

Set product2 = products1.Item("LaVisserie")

Set products2 = product2.Products

Dim product7 As Product
Set product7 = products2.AddNewProduct("setOutil")

Dim products5 As Products
Set products5 = product7.Products

Dim arrayOfVariantOfBSTR2(0)
arrayOfVariantOfBSTR2(0) = "D:\documents\Centrale Lyon\S8\PLM\insertion_vis\catalogue_vis_ecrou_rondelle\outils\male_1,5.CATPart"
Set products5Variant = products5
products5Variant.AddComponentsFromFiles arrayOfVariantOfBSTR2, "All"

Set products5 = product7.Products

Dim product8 As Product
Set product8 = products5.Item("male_1,5.1")

Dim publications1 As Publications
Set publications1 = product8.Publications

Dim publication1 As Publication
Set publication1 = publications1.Item("Axe_petit")

Set publications1 = product8.Publications

Dim publication2 As Publication
Set publication2 = publications1.Item("Face_petit")

Dim arrayOfVariantOfBSTR3(0)
arrayOfVariantOfBSTR3(0) = "D:\documents\Centrale Lyon\S8\PLM\insertion_vis\catalogue_vis_ecrou_rondelle\outils\douille_.CATPart"
Set products5Variant = products5
products5Variant.AddComponentsFromFiles arrayOfVariantOfBSTR3, "All"

Set products5 = product7.Products

Set Nothing1 = products5.Item("douille_.1")

Set productDocument1 = CATIA.ActiveDocument

Dim selection4 As Selection
Set selection4 = productDocument1.Selection

selection4.Clear

selection4.Add product7

selection4.Delete

Set productDocument1 = CATIA.ActiveDocument

Set product1 = productDocument1.Product

Set products1 = product1.Products

Set productDocument1 = CATIA.ActiveDocument

Dim selection5 As Selection
Set selection5 = productDocument1.Selection

selection5.Search "Name=LaVisserie*,all"

Dim long2 As Long
long2 = selection5.Count

Set productDocument1 = CATIA.ActiveDocument

Set product1 = productDocument1.Product

Set products1 = product1.Products

Set product2 = products1.Item("LaVisserie")

Dim bSTR7 As String
bSTR7 = product2.DescriptionRef

Set productDocument1 = CATIA.ActiveDocument

Set selection5 = productDocument1.Selection

selection5.Clear

Dim arrayOfVariantOfBSTR4(0)
arrayOfVariantOfBSTR4(0) = "Part"
Dim bSTR8 As String
Set selection5Variant = selection5
bSTR8 = selection5Variant.SelectElement2(arrayOfVariantOfBSTR4, "Sélectionner un élément de la visserie", False)

Dim selectedElement3 As SelectedElement
Set selectedElement3 = selection5.Item(1)

Set product5 = selectedElement3.LeafProduct

Set products3 = product5.Parent

Set product4 = products3.Parent

Dim bSTR9 As String
bSTR9 = product4.PartNumber

Dim selectedElement4 As SelectedElement
Set selectedElement4 = selection5.Item(1)

Set product5 = selectedElement4.LeafProduct

Set products3 = product5.Parent

Set product4 = products3.Parent

Set products3 = product4.Products

Set product5 = products3.Item(1)

Set product6 = products3.Item(2)

Dim bSTR10 As String
bSTR10 = product5.PartNumber

Dim bSTR11 As String
bSTR11 = product5.PartNumber

selection5.Clear

Set products3 = product4.Products

Set product5 = products3.Item(1)

Set product6 = products3.Item(2)

Dim bSTR12 As String
bSTR12 = product5.PartNumber

Set productDocument1 = CATIA.ActiveDocument

Set product1 = productDocument1.Product

Set products1 = product1.Products

Set productDocument1 = CATIA.ActiveDocument

Set product1 = productDocument1.Product

Set products1 = product1.Products

Set product2 = products1.Item("LaVisserie")

Set products2 = product2.Products

Dim product9 As Product
Set product9 = products2.AddNewProduct("setOutil")

Dim products6 As Products
Set products6 = product9.Products

Dim arrayOfVariantOfBSTR5(0)
arrayOfVariantOfBSTR5(0) = "D:\documents\Centrale Lyon\S8\PLM\insertion_vis\catalogue_vis_ecrou_rondelle\outils\male_1,5.CATPart"
Set products6Variant = products6
products6Variant.AddComponentsFromFiles arrayOfVariantOfBSTR5, "All"

Set products6 = product9.Products

Dim product10 As Product
Set product10 = products6.Item("male_1,5.1")

Dim publications2 As Publications
Set publications2 = product10.Publications

Dim publication3 As Publication
Set publication3 = publications2.Item("Axe_grand")

Set publications2 = product10.Publications

Dim publication4 As Publication
Set publication4 = publications2.Item("Face_grand")

Dim arrayOfVariantOfBSTR6(0)
arrayOfVariantOfBSTR6(0) = "D:\documents\Centrale Lyon\S8\PLM\insertion_vis\catalogue_vis_ecrou_rondelle\outils\douille_.CATPart"
Set products6Variant = products6
products6Variant.AddComponentsFromFiles arrayOfVariantOfBSTR6, "All"

Set products6 = product9.Products

Set Nothing1 = products6.Item("douille_.1")

Set productDocument1 = CATIA.ActiveDocument

Dim selection6 As Selection
Set selection6 = productDocument1.Selection

selection6.Clear

Dim arrayOfVariantOfBSTR7(0)
arrayOfVariantOfBSTR7(0) = "Part"
Dim bSTR13 As String
Set selection6Variant = selection6
bSTR13 = selection6Variant.SelectElement2(arrayOfVariantOfBSTR7, "Sélectionner un élément de la visserie", False)

Dim selectedElement5 As SelectedElement
Set selectedElement5 = selection6.Item(1)

Set product5 = selectedElement5.LeafProduct

Set products3 = product5.Parent

Set product4 = products3.Parent

Dim bSTR14 As String
bSTR14 = product4.PartNumber

Dim selectedElement6 As SelectedElement
Set selectedElement6 = selection6.Item(1)

Set product5 = selectedElement6.LeafProduct

Set products3 = product5.Parent

Set product4 = products3.Parent

Set products3 = product4.Products

Set product5 = products3.Item(1)

Set product6 = products3.Item(2)

Dim bSTR15 As String
bSTR15 = product5.PartNumber

Dim bSTR16 As String
bSTR16 = product5.PartNumber

selection6.Clear

Set products3 = product4.Products

Set product5 = products3.Item(1)

Set product6 = products3.Item(2)

Dim bSTR17 As String
bSTR17 = product5.PartNumber

Set productDocument1 = CATIA.ActiveDocument

Set product1 = productDocument1.Product

Set products1 = product1.Products

Set productDocument1 = CATIA.ActiveDocument

Set product1 = productDocument1.Product

Set products1 = product1.Products

Set product2 = products1.Item("LaVisserie")

Set products2 = product2.Products

Dim product11 As Product
Set product11 = products2.AddNewProduct("setOutil")

Dim products7 As Products
Set products7 = product11.Products

Dim arrayOfVariantOfBSTR8(0)
arrayOfVariantOfBSTR8(0) = "outils\male_1,5.CATPart"
Set products7Variant = products7
products7Variant.AddComponentsFromFiles arrayOfVariantOfBSTR8, "All"

Set products7 = product11.Products

Set Nothing1 = products7.Item("male_1,5.1")

Set productDocument1 = CATIA.ActiveDocument

Set product1 = productDocument1.Product

Set products1 = product1.Products

Set productDocument1 = CATIA.ActiveDocument

Dim selection7 As Selection
Set selection7 = productDocument1.Selection

selection7.Search "Name=LaVisserie*,all"

Dim long3 As Long
long3 = selection7.Count

Set productDocument1 = CATIA.ActiveDocument

Set product1 = productDocument1.Product

Set products1 = product1.Products

Set product2 = products1.Item("LaVisserie")

Dim bSTR18 As String
bSTR18 = product2.DescriptionRef

Set productDocument1 = CATIA.ActiveDocument

Set selection7 = productDocument1.Selection

selection7.Clear

Dim arrayOfVariantOfBSTR9(0)
arrayOfVariantOfBSTR9(0) = "Part"
Dim bSTR19 As String
Set selection7Variant = selection7
bSTR19 = selection7Variant.SelectElement2(arrayOfVariantOfBSTR9, "Sélectionner un élément de la visserie", False)

Dim selectedElement7 As SelectedElement
Set selectedElement7 = selection7.Item(1)

Set product5 = selectedElement7.LeafProduct

Set products3 = product5.Parent

Set product4 = products3.Parent

Dim bSTR20 As String
bSTR20 = product4.PartNumber

Dim selectedElement8 As SelectedElement
Set selectedElement8 = selection7.Item(1)

Set product5 = selectedElement8.LeafProduct

Set products3 = product5.Parent

Set product4 = products3.Parent

Set products3 = product4.Products

Set product5 = products3.Item(1)

Set product6 = products3.Item(2)

Dim bSTR21 As String
bSTR21 = product5.PartNumber

Dim bSTR22 As String
bSTR22 = product5.PartNumber

selection7.Clear

Set products3 = product4.Products

Set product5 = products3.Item(1)

Set product6 = products3.Item(2)

Dim bSTR23 As String
bSTR23 = product5.PartNumber

Set productDocument1 = CATIA.ActiveDocument

Set product1 = productDocument1.Product

Set products1 = product1.Products

Set productDocument1 = CATIA.ActiveDocument

Set product1 = productDocument1.Product

Set products1 = product1.Products

Set product2 = products1.Item("LaVisserie")

Set products2 = product2.Products

Dim product12 As Product
Set product12 = products2.AddNewProduct("setOutil")

Dim products8 As Products
Set products8 = product12.Products

Dim arrayOfVariantOfBSTR10(0)
arrayOfVariantOfBSTR10(0) = "D:\documents\Centrale Lyon\S8\PLM\insertion_vis\catalogue_vis_ecrou_rondelle\outils\male_1,5.CATPart"
Set products8Variant = products8
products8Variant.AddComponentsFromFiles arrayOfVariantOfBSTR10, "All"

Set products8 = product12.Products

Dim product13 As Product
Set product13 = products8.Item("male_1,5.1")

Dim publications3 As Publications
Set publications3 = product13.Publications

Dim publication5 As Publication
Set publication5 = publications3.Item("Axe_grand")

Set publications3 = product13.Publications

Dim publication6 As Publication
Set publication6 = publications3.Item("Face_grand")

Dim arrayOfVariantOfBSTR11(0)
arrayOfVariantOfBSTR11(0) = "D:\documents\Centrale Lyon\S8\PLM\insertion_vis\catalogue_vis_ecrou_rondelle\outils\plate_4.CATPart"
Set products8Variant = products8
products8Variant.AddComponentsFromFiles arrayOfVariantOfBSTR11, "All"

Set products8 = product12.Products

Dim product14 As Product
Set product14 = products8.Item("plate_4.1")

Dim publications4 As Publications
Set publications4 = product14.Publications

Dim publication7 As Publication
Set publication7 = publications4.Item("Axe")

Set publications4 = product14.Publications

Dim publication8 As Publication
Set publication8 = publications4.Item("Face_inf")

Dim publications5 As Publications
Set publications5 = product5.Publications

Dim publication9 As Publication
Set publication9 = publications5.Item("AxeVis")

Set publications5 = product5.Publications

Dim publication10 As Publication
Set publication10 = publications5.Item("FaceRondelle")

Dim publications6 As Publications
Set publications6 = product6.Publications

Dim publication11 As Publication
Set publication11 = publications6.Item("FaceRondelle")

Set productDocument1 = CATIA.ActiveDocument

Set selection7 = productDocument1.Selection

selection7.Clear

Dim bSTR24 As String
bSTR24 = product12.Name

Set products2 = product2.Products

Set product12 = products2.Item("setOutil2.3")

selection7.Add product12

CATIA.StartCommand "Flexible/rigide"

selection7.Clear

Set constraints1 = product1.Connections("CATIAConstraints")

Dim reference1 As Reference
' No resolution found for the object reference1...

Dim reference2 As Reference
' No resolution found for the object reference2...

Dim constraint2 As Constraint
Set constraint2 = constraints1.AddBiEltCst(catCstTypeOn, reference1, reference2)

Set productDocument1 = CATIA.ActiveDocument

Set product1 = productDocument1.Product

product1.Update

Set productDocument1 = CATIA.ActiveDocument

Set selection7 = productDocument1.Selection

selection7.Clear

Dim arrayOfVariantOfBSTR12(0)
arrayOfVariantOfBSTR12(0) = "Part"
Dim bSTR25 As String
Set selection7Variant = selection7
bSTR25 = selection7Variant.SelectElement2(arrayOfVariantOfBSTR12, "Sélectionner un élément de la visserie", False)

Dim selectedElement9 As SelectedElement
Set selectedElement9 = selection7.Item(1)

Set product5 = selectedElement9.LeafProduct

Set products3 = product5.Parent

Set product4 = products3.Parent

Dim bSTR26 As String
bSTR26 = product4.PartNumber

Dim selectedElement10 As SelectedElement
Set selectedElement10 = selection7.Item(1)

Set product5 = selectedElement10.LeafProduct

Set products3 = product5.Parent

Set product4 = products3.Parent

Set products3 = product4.Products

Set product5 = products3.Item(1)

Set product6 = products3.Item(2)

Dim bSTR27 As String
bSTR27 = product5.PartNumber

Dim bSTR28 As String
bSTR28 = product5.PartNumber

selection7.Clear

Set products3 = product4.Products

Set product5 = products3.Item(1)

Set product6 = products3.Item(2)

Dim bSTR29 As String
bSTR29 = product5.PartNumber

Set productDocument1 = CATIA.ActiveDocument

Set product1 = productDocument1.Product

Set products1 = product1.Products

Set productDocument1 = CATIA.ActiveDocument

Set product1 = productDocument1.Product

Set products1 = product1.Products

Set product2 = products1.Item("LaVisserie")

Set products2 = product2.Products

Dim product15 As Product
Set product15 = products2.AddNewProduct("setOutil")

Dim products9 As Products
Set products9 = product15.Products

Dim arrayOfVariantOfBSTR13(0)
arrayOfVariantOfBSTR13(0) = "D:\documents\Centrale Lyon\S8\PLM\insertion_vis\catalogue_vis_ecrou_rondelle\outils\male_1,5.CATPart"
Set products9Variant = products9
products9Variant.AddComponentsFromFiles arrayOfVariantOfBSTR13, "All"

Set products9 = product15.Products

Dim product16 As Product
Set product16 = products9.Item("male_1,5.1")

Dim publications7 As Publications
Set publications7 = product16.Publications

Dim publication12 As Publication
Set publication12 = publications7.Item("Axe_grand")

Set publications7 = product16.Publications

Dim publication13 As Publication
Set publication13 = publications7.Item("Face_grand")

Dim arrayOfVariantOfBSTR14(0)
arrayOfVariantOfBSTR14(0) = "D:\documents\Centrale Lyon\S8\PLM\insertion_vis\catalogue_vis_ecrou_rondelle\outils\plate_4.CATPart"
Set products9Variant = products9
products9Variant.AddComponentsFromFiles arrayOfVariantOfBSTR14, "All"

Set products9 = product15.Products

Dim product17 As Product
Set product17 = products9.Item("plate_4.1")

Dim publications8 As Publications
Set publications8 = product17.Publications

Dim publication14 As Publication
Set publication14 = publications8.Item("Axe")

Set publications8 = product17.Publications

Dim publication15 As Publication
Set publication15 = publications8.Item("Face_inf")

Set publications5 = product5.Publications

Set publication9 = publications5.Item("AxeVis")

Set publications5 = product5.Publications

Set publication10 = publications5.Item("FaceRondelle")

Set publications6 = product6.Publications

Set publication11 = publications6.Item("FaceRondelle")

Set productDocument1 = CATIA.ActiveDocument

Set selection7 = productDocument1.Selection

selection7.Clear

Dim bSTR30 As String
bSTR30 = product15.Name

Set products2 = product2.Products

Set product15 = products2.Item("setOutil3.2")

selection7.Add product15

CATIA.StartCommand "Flexible/rigide"

selection7.Clear

Set constraints1 = product1.Connections("CATIAConstraints")

Dim reference3 As Reference
' No resolution found for the object reference3...

Dim constraint3 As Constraint
Set constraint3 = constraints1.AddBiEltCst(catCstTypeOn, reference3, reference2)

Set productDocument1 = CATIA.ActiveDocument

Set product1 = productDocument1.Product

product1.Update

Set products3 = product4.Products

Set product5 = products3.Item(1)

Set product6 = products3.Item(2)

Dim bSTR31 As String
bSTR31 = product5.PartNumber

Set productDocument1 = CATIA.ActiveDocument

Set product1 = productDocument1.Product

Set products1 = product1.Products

Set productDocument1 = CATIA.ActiveDocument

Set product1 = productDocument1.Product

Set products1 = product1.Products

Set product2 = products1.Item("LaVisserie")

Set products2 = product2.Products

Dim product18 As Product
Set product18 = products2.AddNewProduct("setOutil")

Dim products10 As Products
Set products10 = product18.Products

Dim arrayOfVariantOfBSTR15(0)
arrayOfVariantOfBSTR15(0) = "D:\documents\Centrale Lyon\S8\PLM\insertion_vis\catalogue_vis_ecrou_rondelle\outils\male_1,5.CATPart"
Set products10Variant = products10
products10Variant.AddComponentsFromFiles arrayOfVariantOfBSTR15, "All"

Set products10 = product18.Products

Dim product19 As Product
Set product19 = products10.Item("male_1,5.1")

Dim publications9 As Publications
Set publications9 = product19.Publications

Dim publication16 As Publication
Set publication16 = publications9.Item("Axe_grand")

Set publications9 = product19.Publications

Dim publication17 As Publication
Set publication17 = publications9.Item("Face_grand")

Dim arrayOfVariantOfBSTR16(0)
arrayOfVariantOfBSTR16(0) = "D:\documents\Centrale Lyon\S8\PLM\insertion_vis\catalogue_vis_ecrou_rondelle\outils\douille_.CATPart"
Set products10Variant = products10
products10Variant.AddComponentsFromFiles arrayOfVariantOfBSTR16, "All"

Set products10 = product18.Products

Set Nothing1 = products10.Item("douille_.1")

Set productDocument1 = CATIA.ActiveDocument

Set product1 = productDocument1.Product

Set products1 = product1.Products

Set productDocument1 = CATIA.ActiveDocument

Dim selection8 As Selection
Set selection8 = productDocument1.Selection

selection8.Search "Name=LaVisserie*,all"

Dim long4 As Long
long4 = selection8.Count

Set productDocument1 = CATIA.ActiveDocument

Set product1 = productDocument1.Product

Set products1 = product1.Products

Set product2 = products1.Item("LaVisserie")

Dim bSTR32 As String
bSTR32 = product2.DescriptionRef

Set productDocument1 = CATIA.ActiveDocument

Set selection8 = productDocument1.Selection

selection8.Clear

Dim arrayOfVariantOfBSTR17(0)
arrayOfVariantOfBSTR17(0) = "Part"
Dim bSTR33 As String
Set selection8Variant = selection8
bSTR33 = selection8Variant.SelectElement2(arrayOfVariantOfBSTR17, "Sélectionner un élément de la visserie", False)

Dim selectedElement11 As SelectedElement
Set selectedElement11 = selection8.Item(1)

Set product5 = selectedElement11.LeafProduct

Set products3 = product5.Parent

Set product4 = products3.Parent

Dim bSTR34 As String
bSTR34 = product4.PartNumber

Dim selectedElement12 As SelectedElement
Set selectedElement12 = selection8.Item(1)

Set product5 = selectedElement12.LeafProduct

Set products3 = product5.Parent

Set product4 = products3.Parent

Set products3 = product4.Products

Set product5 = products3.Item(1)

Set product6 = products3.Item(2)

Dim bSTR35 As String
bSTR35 = product5.PartNumber

Dim bSTR36 As String
bSTR36 = product5.PartNumber

selection8.Clear

Set products3 = product4.Products

Set product5 = products3.Item(1)

Set product6 = products3.Item(2)

Dim bSTR37 As String
bSTR37 = product5.PartNumber

Set productDocument1 = CATIA.ActiveDocument

Set product1 = productDocument1.Product

Set products1 = product1.Products

Set productDocument1 = CATIA.ActiveDocument

Set product1 = productDocument1.Product

Set products1 = product1.Products

Set product2 = products1.Item("LaVisserie")

Set products2 = product2.Products

Dim product20 As Product
Set product20 = products2.AddNewProduct("setOutil")

Dim products11 As Products
Set products11 = product20.Products

Dim arrayOfVariantOfBSTR18(0)
arrayOfVariantOfBSTR18(0) = "D:\documents\Centrale Lyon\S8\PLM\insertion_vis\catalogue_vis_ecrou_rondelle\outils\male_1,5.CATPart"
Set products11Variant = products11
products11Variant.AddComponentsFromFiles arrayOfVariantOfBSTR18, "All"

Set products11 = product20.Products

Dim product21 As Product
Set product21 = products11.Item("male_1,5.1")

Dim publications10 As Publications
Set publications10 = product21.Publications

Dim publication18 As Publication
Set publication18 = publications10.Item("Axe_grand")

Set publications10 = product21.Publications

Dim publication19 As Publication
Set publication19 = publications10.Item("Face_grand")

Dim arrayOfVariantOfBSTR19(0)
arrayOfVariantOfBSTR19(0) = "D:\documents\Centrale Lyon\S8\PLM\insertion_vis\catalogue_vis_ecrou_rondelle\outils\douille_4.CATPart"
Set products11Variant = products11
products11Variant.AddComponentsFromFiles arrayOfVariantOfBSTR19, "All"

Set products11 = product20.Products

Set Nothing1 = products11.Item("douille_4.1")

Set productDocument1 = CATIA.ActiveDocument

Dim selection9 As Selection
Set selection9 = productDocument1.Selection

selection9.Clear

selection9.Add constraint3

selection9.Add constraint2

selection9.Add product20

selection9.Add product18

selection9.Add product15

selection9.Add product12

selection9.Add product11

selection9.Add product9

selection9.Delete

Set productDocument1 = CATIA.ActiveDocument

Set product1 = productDocument1.Product

Set products1 = product1.Products

Set productDocument1 = CATIA.ActiveDocument

Dim selection10 As Selection
Set selection10 = productDocument1.Selection

selection10.Search "Name=LaVisserie*,all"

Dim long5 As Long
long5 = selection10.Count

Set productDocument1 = CATIA.ActiveDocument

Set product1 = productDocument1.Product

Set products1 = product1.Products

Set product2 = products1.Item("LaVisserie")

Dim bSTR38 As String
bSTR38 = product2.DescriptionRef

Set productDocument1 = CATIA.ActiveDocument

Set selection10 = productDocument1.Selection

selection10.Clear

Dim arrayOfVariantOfBSTR20(0)
arrayOfVariantOfBSTR20(0) = "Part"
Dim bSTR39 As String
Set selection10Variant = selection10
bSTR39 = selection10Variant.SelectElement2(arrayOfVariantOfBSTR20, "Sélectionner un élément de la visserie", False)

Dim selectedElement13 As SelectedElement
Set selectedElement13 = selection10.Item(1)

Set product5 = selectedElement13.LeafProduct

Set products3 = product5.Parent

Set product4 = products3.Parent

Dim bSTR40 As String
bSTR40 = product4.PartNumber

Dim selectedElement14 As SelectedElement
Set selectedElement14 = selection10.Item(1)

Set product5 = selectedElement14.LeafProduct

Set products3 = product5.Parent

Set product4 = products3.Parent

Set products3 = product4.Products

Set product5 = products3.Item(1)

Set product6 = products3.Item(2)

Dim bSTR41 As String
bSTR41 = product5.PartNumber

Dim bSTR42 As String
bSTR42 = product5.PartNumber

selection10.Clear

Set products3 = product4.Products

Set product5 = products3.Item(1)

Set product6 = products3.Item(2)

Dim bSTR43 As String
bSTR43 = product5.PartNumber

Set productDocument1 = CATIA.ActiveDocument

Set product1 = productDocument1.Product

Set products1 = product1.Products

Set productDocument1 = CATIA.ActiveDocument

Set product1 = productDocument1.Product

Set products1 = product1.Products

Set product2 = products1.Item("LaVisserie")

Set products2 = product2.Products

Dim product22 As Product
Set product22 = products2.AddNewProduct("setOutil")

Dim products12 As Products
Set products12 = product22.Products

Dim arrayOfVariantOfBSTR21(0)
arrayOfVariantOfBSTR21(0) = "D:\documents\Centrale Lyon\S8\PLM\insertion_vis\catalogue_vis_ecrou_rondelle\outils\male_1,5.CATPart"
Set products12Variant = products12
products12Variant.AddComponentsFromFiles arrayOfVariantOfBSTR21, "All"

Set products12 = product22.Products

Dim product23 As Product
Set product23 = products12.Item("male_1,5.1")

Dim publications11 As Publications
Set publications11 = product23.Publications

Dim publication20 As Publication
Set publication20 = publications11.Item("Axe_grand")

Set publications11 = product23.Publications

Dim publication21 As Publication
Set publication21 = publications11.Item("Face_grand")

Dim arrayOfVariantOfBSTR22(0)
arrayOfVariantOfBSTR22(0) = "D:\documents\Centrale Lyon\S8\PLM\insertion_vis\catalogue_vis_ecrou_rondelle\outils\douille_4.CATPart"
Set products12Variant = products12
products12Variant.AddComponentsFromFiles arrayOfVariantOfBSTR22, "All"

Set products12 = product22.Products

Set Nothing1 = products12.Item("douille_4.1")

Set productDocument1 = CATIA.ActiveDocument

Dim selection11 As Selection
Set selection11 = productDocument1.Selection

selection11.Clear

selection11.Add product22

selection11.Delete

Set productDocument1 = CATIA.ActiveDocument

Set product1 = productDocument1.Product

Set products1 = product1.Products

Set productDocument1 = CATIA.ActiveDocument

Dim selection12 As Selection
Set selection12 = productDocument1.Selection

selection12.Search "Name=LaVisserie*,all"

Dim long6 As Long
long6 = selection12.Count

Set productDocument1 = CATIA.ActiveDocument

Set product1 = productDocument1.Product

Set products1 = product1.Products

Set product2 = products1.Item("LaVisserie")

Dim bSTR44 As String
bSTR44 = product2.DescriptionRef

Set productDocument1 = CATIA.ActiveDocument

Set selection12 = productDocument1.Selection

selection12.Clear

Dim arrayOfVariantOfBSTR23(0)
arrayOfVariantOfBSTR23(0) = "Part"
Dim bSTR45 As String
Set selection12Variant = selection12
bSTR45 = selection12Variant.SelectElement2(arrayOfVariantOfBSTR23, "Sélectionner un élément de la visserie", False)

Dim selectedElement15 As SelectedElement
Set selectedElement15 = selection12.Item(1)

Set product5 = selectedElement15.LeafProduct

Set products3 = product5.Parent

Set product4 = products3.Parent

Dim bSTR46 As String
bSTR46 = product4.PartNumber

Dim selectedElement16 As SelectedElement
Set selectedElement16 = selection12.Item(1)

Set product5 = selectedElement16.LeafProduct

Set products3 = product5.Parent

Set product4 = products3.Parent

Set products3 = product4.Products

Set product5 = products3.Item(1)

Set product6 = products3.Item(2)

Dim bSTR47 As String
bSTR47 = product5.PartNumber

Dim bSTR48 As String
bSTR48 = product5.PartNumber

selection12.Clear

Set products3 = product4.Products

Set product5 = products3.Item(1)

Set product6 = products3.Item(2)

Dim bSTR49 As String
bSTR49 = product5.PartNumber

Set productDocument1 = CATIA.ActiveDocument

Set product1 = productDocument1.Product

Set products1 = product1.Products

Set productDocument1 = CATIA.ActiveDocument

Set product1 = productDocument1.Product

Set products1 = product1.Products

Set product2 = products1.Item("LaVisserie")

Set products2 = product2.Products

Dim product24 As Product
Set product24 = products2.AddNewProduct("setOutil")

Dim products13 As Products
Set products13 = product24.Products

Dim arrayOfVariantOfBSTR24(0)
arrayOfVariantOfBSTR24(0) = "D:\documents\Centrale Lyon\S8\PLM\insertion_vis\catalogue_vis_ecrou_rondelle\outils\male_1,5.CATPart"
Set products13Variant = products13
products13Variant.AddComponentsFromFiles arrayOfVariantOfBSTR24, "All"

Set products13 = product24.Products

Dim product25 As Product
Set product25 = products13.Item("male_1,5.1")

Dim publications12 As Publications
Set publications12 = product25.Publications

Dim publication22 As Publication
Set publication22 = publications12.Item("Axe_grand")

Set publications12 = product25.Publications

Dim publication23 As Publication
Set publication23 = publications12.Item("Face_grand")

Dim arrayOfVariantOfBSTR25(0)
arrayOfVariantOfBSTR25(0) = "D:\documents\Centrale Lyon\S8\PLM\insertion_vis\catalogue_vis_ecrou_rondelle\outils\douille_4.CATPart"
Set products13Variant = products13
products13Variant.AddComponentsFromFiles arrayOfVariantOfBSTR25, "All"

Set products13 = product24.Products

Set Nothing1 = products13.Item("douille_4.1")

Dim documents1 As Documents
Set documents1 = CATIA.Documents

Dim partDocument1 As PartDocument
Set partDocument1 = documents1.Item("part de test.CATPart")

Dim part1 As Part
Set part1 = partDocument1.Part

Dim bodies1 As Bodies
Set bodies1 = part1.Bodies

Dim body1 As Body
Set body1 = bodies1.Item("Corps principal")

Dim shapes1 As Shapes
Set shapes1 = body1.Shapes

Dim pad1 As Pad
Set pad1 = shapes1.Item("Extrusion.1")

Dim sketch1 As Sketch
Set sketch1 = pad1.Sketch

part1.InWorkObject = sketch1

Dim factory2D1 As Factory2D
Set factory2D1 = sketch1.OpenEdition()

Dim geometricElements1 As GeometricElements
Set geometricElements1 = sketch1.GeometricElements

Dim circle2D1 As Circle2D
Set circle2D1 = geometricElements1.Item("Cercle.1")

circle2D1.SetData 5.320567, 5.445413, 2#

Dim constraints2 As Constraints
Set constraints2 = sketch1.Constraints

Dim constraint4 As Constraint
Set constraint4 = constraints2.Item("Rayon.5")

Dim length1 As Length
Set length1 = constraint4.Dimension

length1.Value = 2#

sketch1.CloseEdition

part1.InWorkObject = pad1

part1.Update

Set productDocument1 = CATIA.ActiveDocument

Dim selection13 As Selection
Set selection13 = productDocument1.Selection

selection13.Clear

selection13.Add product24

selection13.Delete

Set productDocument1 = CATIA.ActiveDocument

Set product1 = productDocument1.Product

Set products1 = product1.Products

Set productDocument1 = CATIA.ActiveDocument

Dim selection14 As Selection
Set selection14 = productDocument1.Selection

selection14.Search "Name=LaVisserie*,all"

Dim long7 As Long
long7 = selection14.Count

Set productDocument1 = CATIA.ActiveDocument

Set product1 = productDocument1.Product

Set products1 = product1.Products

Set product2 = products1.Item("LaVisserie")

Dim bSTR50 As String
bSTR50 = product2.DescriptionRef

Set productDocument1 = CATIA.ActiveDocument

Set selection14 = productDocument1.Selection

selection14.Clear

Dim arrayOfVariantOfBSTR26(0)
arrayOfVariantOfBSTR26(0) = "Part"
Dim bSTR51 As String
Set selection14Variant = selection14
bSTR51 = selection14Variant.SelectElement2(arrayOfVariantOfBSTR26, "Sélectionner un élément de la visserie", False)

Dim selectedElement17 As SelectedElement
Set selectedElement17 = selection14.Item(1)

Set product5 = selectedElement17.LeafProduct

Set products3 = product5.Parent

Set product4 = products3.Parent

Dim bSTR52 As String
bSTR52 = product4.PartNumber

Dim selectedElement18 As SelectedElement
Set selectedElement18 = selection14.Item(1)

Set product5 = selectedElement18.LeafProduct

Set products3 = product5.Parent

Set product4 = products3.Parent

Set products3 = product4.Products

Set product5 = products3.Item(1)

Set product6 = products3.Item(2)

Dim bSTR53 As String
bSTR53 = product5.PartNumber

Dim bSTR54 As String
bSTR54 = product6.PartNumber

Dim bSTR55 As String
bSTR55 = product5.PartNumber

Dim bSTR56 As String
bSTR56 = product5.PartNumber

Dim bSTR57 As String
bSTR57 = product5.PartNumber

Dim bSTR58 As String
bSTR58 = product5.PartNumber

Dim bSTR59 As String
bSTR59 = product5.PartNumber

Dim bSTR60 As String
bSTR60 = product5.PartNumber

Dim bSTR61 As String
bSTR61 = product5.PartNumber

Dim bSTR62 As String
bSTR62 = product5.PartNumber

Set products3 = product4.Products

Set Nothing1 = products3.ReplaceComponent(product5, "C:\CATIA\Vis parametrique\catalogue_vis_ecrou_rondelle\2x16CHC.CATPart", True)

Set productDocument1 = CATIA.ActiveDocument

Set product1 = productDocument1.Product

product1.Update

Set products3 = product4.Products

Set product5 = products3.Item(1)

Set product6 = products3.Item(2)

Dim bSTR63 As String
bSTR63 = product5.PartNumber

Dim bSTR64 As String
bSTR64 = product6.PartNumber

Dim bSTR65 As String
bSTR65 = product5.PartNumber

Dim bSTR66 As String
bSTR66 = product5.PartNumber

Dim bSTR67 As String
bSTR67 = product5.PartNumber

Dim bSTR68 As String
bSTR68 = product5.PartNumber

Dim bSTR69 As String
bSTR69 = product5.PartNumber

Dim bSTR70 As String
bSTR70 = product5.PartNumber

Dim bSTR71 As String
bSTR71 = product5.PartNumber

Dim bSTR72 As String
bSTR72 = product5.PartNumber

Dim bSTR73 As String
bSTR73 = product6.PartNumber

Dim bSTR74 As String
bSTR74 = product6.PartNumber

Set products3 = product4.Products

Set Nothing1 = products3.ReplaceComponent(product6, "C:\CATIA\Vis parametrique\catalogue_vis_ecrou_rondelle\ecrou_M2_NS.CATPart", True)

Set productDocument1 = CATIA.ActiveDocument

Set product1 = productDocument1.Product

product1.Update

Set products3 = product4.Products

Set product5 = products3.Item(1)

Set product6 = products3.Item(2)

Dim bSTR75 As String
bSTR75 = product5.PartNumber

Dim bSTR76 As String
bSTR76 = product6.PartNumber

Dim bSTR77 As String
bSTR77 = product5.PartNumber

Dim bSTR78 As String
bSTR78 = product5.PartNumber

Dim bSTR79 As String
bSTR79 = product5.PartNumber

Dim bSTR80 As String
bSTR80 = product5.PartNumber

Dim bSTR81 As String
bSTR81 = product5.PartNumber

Dim bSTR82 As String
bSTR82 = product5.PartNumber

Dim bSTR83 As String
bSTR83 = product5.PartNumber

Dim bSTR84 As String
bSTR84 = product5.PartNumber

Dim bSTR85 As String
bSTR85 = product6.PartNumber

Dim bSTR86 As String
bSTR86 = product6.PartNumber

Dim long8 As Long
long8 = products3.Count

Dim product26 As Product
Set product26 = products3.Item(3)

Dim product27 As Product
Set product27 = products3.Item(4)

Dim bSTR87 As String
bSTR87 = product26.PartNumber

Dim bSTR88 As String
bSTR88 = product26.PartNumber

Dim bSTR89 As String
bSTR89 = product26.PartNumber

Set products3 = product4.Products

Set Nothing1 = products3.ReplaceComponent(product26, "C:\CATIA\Vis parametrique\catalogue_vis_ecrou_rondelle\rondelle_M2.CATPart", True)

Set products3 = product4.Products

Set Nothing1 = products3.ReplaceComponent(product27, "C:\CATIA\Vis parametrique\catalogue_vis_ecrou_rondelle\rondelle_M2.CATPart", True)

Set productDocument1 = CATIA.ActiveDocument

Set product1 = productDocument1.Product

product1.Update

Set products3 = product4.Products

Set product5 = products3.Item(1)

Set product6 = products3.Item(2)

Dim bSTR90 As String
bSTR90 = product5.PartNumber

Dim bSTR91 As String
bSTR91 = product6.PartNumber

Dim bSTR92 As String
bSTR92 = product5.PartNumber

Dim bSTR93 As String
bSTR93 = product5.PartNumber

Dim bSTR94 As String
bSTR94 = product5.PartNumber

Dim bSTR95 As String
bSTR95 = product5.PartNumber

Dim bSTR96 As String
bSTR96 = product5.PartNumber

Dim bSTR97 As String
bSTR97 = product5.PartNumber

Dim bSTR98 As String
bSTR98 = product5.PartNumber

Dim bSTR99 As String
bSTR99 = product5.PartNumber

Dim bSTR100 As String
bSTR100 = product6.PartNumber

Dim bSTR101 As String
bSTR101 = product6.PartNumber

Dim long9 As Long
long9 = products3.Count

Set product26 = products3.Item(3)

Set product27 = products3.Item(4)

Dim bSTR102 As String
bSTR102 = product26.PartNumber

Dim bSTR103 As String
bSTR103 = product26.PartNumber

Dim bSTR104 As String
bSTR104 = product26.PartNumber

Dim long10 As Long
long10 = products3.Count

Set product26 = products3.Item(3)

Set product27 = products3.Item(4)

Dim bSTR105 As String
bSTR105 = product26.PartNumber

Dim bSTR106 As String
bSTR106 = product26.PartNumber

Dim bSTR107 As String
bSTR107 = product26.PartNumber

Dim bSTR108 As String
bSTR108 = product6.PartNumber

Dim bSTR109 As String
bSTR109 = product6.PartNumber

Dim long11 As Long
long11 = products3.Count

Set product26 = products3.Item(3)

Set product27 = products3.Item(4)

Dim bSTR110 As String
bSTR110 = product26.PartNumber

Dim bSTR111 As String
bSTR111 = product26.PartNumber

Dim bSTR112 As String
bSTR112 = product26.PartNumber

selection14.Clear

Set productDocument1 = CATIA.ActiveDocument

Set selection14 = productDocument1.Selection

selection14.Clear

Dim arrayOfVariantOfBSTR27(0)
arrayOfVariantOfBSTR27(0) = "Part"
Dim bSTR113 As String
Set selection14Variant = selection14
bSTR113 = selection14Variant.SelectElement2(arrayOfVariantOfBSTR27, "Sélectionner un élément de la visserie", False)

Dim selectedElement19 As SelectedElement
Set selectedElement19 = selection14.Item(1)

Set product5 = selectedElement19.LeafProduct

Set products3 = product5.Parent

Set product4 = products3.Parent

Dim bSTR114 As String
bSTR114 = product4.PartNumber

Dim selectedElement20 As SelectedElement
Set selectedElement20 = selection14.Item(1)

Set product5 = selectedElement20.LeafProduct

Set products3 = product5.Parent

Set product4 = products3.Parent

Set products3 = product4.Products

Set product5 = products3.Item(1)

Set product6 = products3.Item(2)

Dim bSTR115 As String
bSTR115 = product5.PartNumber

Dim bSTR116 As String
bSTR116 = product6.PartNumber

Dim long12 As Long
long12 = products3.Count

Set product26 = products3.Item(3)

Set product27 = products3.Item(4)

Dim bSTR117 As String
bSTR117 = product26.PartNumber

Dim bSTR118 As String
bSTR118 = product27.PartNumber

selection14.Clear

Set productDocument1 = CATIA.ActiveDocument

Set product1 = productDocument1.Product

Set constraints1 = product1.Connections("CATIAConstraints")

Dim long13 As Long
long13 = constraints1.Count

Dim constraint5 As Constraint
Set constraint5 = constraints1.Item(2)

Dim reference4 As Reference
Set reference4 = constraint5.GetConstraintElement(1)

Set productDocument1 = CATIA.ActiveDocument

Dim selection15 As Selection
Set selection15 = productDocument1.Selection

selection15.Clear

selection15.Add product4

selection15.Delete

Set product2 = products1.Item("LaVisserie")

Set products2 = product2.Products

Set Nothing1 = products2.Item("setVis.2")

Set product2 = products1.Item("LaVisserie")

Set products2 = product2.Products

Set Nothing1 = products2.Item("setVis.2")

Dim product28 As Product
Set product28 = products1.Item("Pièce1.1")

Dim products14 As Products
Set products14 = product28.Products

Set product2 = products1.Item("LaVisserie")

Set products2 = product2.Products

Set Nothing1 = products2.Item("setVis.2")

Set product2 = products1.Item("LaVisserie")

Set products2 = product2.Products

Set Nothing1 = products2.Item("setVis.2")

Set product2 = products1.Item("LaVisserie")

Set products2 = product2.Products

Set Nothing1 = products2.Item("setVis.2")

Set product2 = products1.Item("LaVisserie")

Set products2 = product2.Products

Set Nothing1 = products2.Item("setVis.2")

Set product2 = products1.Item("LaVisserie")

Set products2 = product2.Products

Set Nothing1 = products2.Item("setVis.2")

Set product28 = products1.Item("Pièce1.1")

Set products14 = product28.Products

Set product2 = products1.Item("LaVisserie")

Set products2 = product2.Products

Set Nothing1 = products2.Item("setVis.2")

Set product2 = products1.Item("LaVisserie")

Set products2 = product2.Products

Set Nothing1 = products2.Item("setVis.2")

Set product2 = products1.Item("LaVisserie")

Set products2 = product2.Products

Set Nothing1 = products2.Item("setVis.2")

Set product2 = products1.Item("LaVisserie")

Set products2 = product2.Products

Set Nothing1 = products2.Item("setVis.2")

Set product2 = products1.Item("LaVisserie")

Set products2 = product2.Products

Set Nothing1 = products2.Item("setVis.2")

Set product2 = products1.Item("LaVisserie")

Set products2 = product2.Products

Set Nothing1 = products2.Item("setVis.2")

Set product2 = products1.Item("LaVisserie")

Set products2 = product2.Products

Set Nothing1 = products2.Item("setVis.2")

Set product2 = products1.Item("LaVisserie")

Set products2 = product2.Products

Set Nothing1 = products2.Item("setVis.2")

Set product2 = products1.Item("LaVisserie")

Set products2 = product2.Products

Set Nothing1 = products2.Item("setVis.2")

Set product2 = products1.Item("LaVisserie")

Set products2 = product2.Products

Set Nothing1 = products2.Item("setVis.2")

Set product2 = products1.Item("LaVisserie")

Set products2 = product2.Products

Set Nothing1 = products2.Item("setVis.2")

Set product2 = products1.Item("LaVisserie")

Set products2 = product2.Products

Set Nothing1 = products2.Item("setVis.2")

Set product2 = products1.Item("LaVisserie")

Set products2 = product2.Products

Set Nothing1 = products2.Item("setVis.2")

Set product2 = products1.Item("LaVisserie")

Set products2 = product2.Products

Set Nothing1 = products2.Item("setVis.2")

Set product2 = products1.Item("LaVisserie")

Set products2 = product2.Products

Set Nothing1 = products2.Item("setVis.2")

Set product2 = products1.Item("LaVisserie")

Set products2 = product2.Products

Set Nothing1 = products2.Item("setVis.2")

Set product2 = products1.Item("LaVisserie")

Set products2 = product2.Products

Set Nothing1 = products2.Item("setVis.2")

Set product2 = products1.Item("LaVisserie")

Set products2 = product2.Products

Set Nothing1 = products2.Item("setVis.2")

Set product2 = products1.Item("LaVisserie")

Set products2 = product2.Products

Set Nothing1 = products2.Item("setVis.2")

Set product2 = products1.Item("LaVisserie")

Set products2 = product2.Products

Set Nothing1 = products2.Item("setVis.2")

Set product2 = products1.Item("LaVisserie")

Set products2 = product2.Products

Set Nothing1 = products2.Item("setVis.2")

Set product2 = products1.Item("LaVisserie")

Set products2 = product2.Products

Set Nothing1 = products2.Item("setVis.2")

Set product2 = products1.Item("LaVisserie")

Set products2 = product2.Products

Set Nothing1 = products2.Item("setVis.2")

Set product2 = products1.Item("LaVisserie")

Set products2 = product2.Products

Set Nothing1 = products2.Item("setVis.2")

Set product2 = products1.Item("LaVisserie")

Set products2 = product2.Products

Set Nothing1 = products2.Item("setVis.2")

Set product28 = products1.Item("Pièce1.1")

Set products14 = product28.Products

Set product2 = products1.Item("LaVisserie")

Set products2 = product2.Products

Set Nothing1 = products2.Item("setVis.2")

Set product2 = products1.Item("LaVisserie")

Set products2 = product2.Products

Set Nothing1 = products2.Item("setVis.2")

Set product2 = products1.Item("LaVisserie")

Set products2 = product2.Products

Set Nothing1 = products2.Item("setVis.2")

Set product2 = products1.Item("LaVisserie")

Set products2 = product2.Products

Set Nothing1 = products2.Item("setVis.2")

Set product2 = products1.Item("LaVisserie")

Set products2 = product2.Products

Set Nothing1 = products2.Item("setVis.2")

Set product28 = products1.Item("Pièce1.1")

Set products14 = product28.Products

Set product2 = products1.Item("LaVisserie")

Set products2 = product2.Products

Set Nothing1 = products2.Item("setVis.2")

Set product2 = products1.Item("LaVisserie")

Set products2 = product2.Products

Set Nothing1 = products2.Item("setVis.2")

Set product2 = products1.Item("LaVisserie")

Set products2 = product2.Products

Set Nothing1 = products2.Item("setVis.2")

Set product28 = products1.Item("Pièce1.1")

Set products14 = product28.Products

Set product2 = products1.Item("LaVisserie")

Set products2 = product2.Products

Set Nothing1 = products2.Item("setVis.2")

Set product2 = products1.Item("LaVisserie")

Set products2 = product2.Products

Set Nothing1 = products2.Item("setVis.2")

Set product2 = products1.Item("LaVisserie")

Set products2 = product2.Products

Set Nothing1 = products2.Item("setVis.2")

Set product2 = products1.Item("LaVisserie")

Set products2 = product2.Products

Set Nothing1 = products2.Item("setVis.2")

Set product2 = products1.Item("LaVisserie")

Set products2 = product2.Products

Set Nothing1 = products2.Item("setVis.2")

Set product2 = products1.Item("LaVisserie")

Set products2 = product2.Products

Set Nothing1 = products2.Item("setVis.2")

Set product2 = products1.Item("LaVisserie")

Set products2 = product2.Products

Set Nothing1 = products2.Item("setVis.2")

Set product28 = products1.Item("Pièce1.1")

Set products14 = product28.Products

Set product2 = products1.Item("LaVisserie")

Set products2 = product2.Products

Set Nothing1 = products2.Item("setVis.2")

Set product2 = products1.Item("LaVisserie")

Set products2 = product2.Products

Set Nothing1 = products2.Item("setVis.2")

Set product2 = products1.Item("LaVisserie")

Set products2 = product2.Products

Set Nothing1 = products2.Item("setVis.2")

Set product2 = products1.Item("LaVisserie")

Set products2 = product2.Products

Set Nothing1 = products2.Item("setVis.2")

Set product2 = products1.Item("LaVisserie")

Set products2 = product2.Products

Set Nothing1 = products2.Item("setVis.2")

Set product2 = products1.Item("LaVisserie")

Set products2 = product2.Products

Set Nothing1 = products2.Item("setVis.2")

Set product2 = products1.Item("LaVisserie")

Set products2 = product2.Products

Set Nothing1 = products2.Item("setVis.2")

Set product2 = products1.Item("LaVisserie")

Set products2 = product2.Products

Set Nothing1 = products2.Item("setVis.2")

Set product2 = products1.Item("LaVisserie")

Set products2 = product2.Products

Set Nothing1 = products2.Item("setVis.2")

Set product2 = products1.Item("LaVisserie")

Set products2 = product2.Products

Set Nothing1 = products2.Item("setVis.2")

Set product2 = products1.Item("LaVisserie")

Set products2 = product2.Products

Set Nothing1 = products2.Item("setVis.2")

Set product2 = products1.Item("LaVisserie")

Set products2 = product2.Products

Set Nothing1 = products2.Item("setVis.2")

Set product2 = products1.Item("LaVisserie")

Set products2 = product2.Products

Set Nothing1 = products2.Item("setVis.2")

Set product2 = products1.Item("LaVisserie")

Set products2 = product2.Products

Set Nothing1 = products2.Item("setVis.2")

Set product2 = products1.Item("LaVisserie")

Set products2 = product2.Products

Set Nothing1 = products2.Item("setVis.2")

Set product2 = products1.Item("LaVisserie")

Set products2 = product2.Products

Set Nothing1 = products2.Item("setVis.2")

Set product2 = products1.Item("LaVisserie")

Set products2 = product2.Products

Set Nothing1 = products2.Item("setVis.2")

Set product2 = products1.Item("LaVisserie")

Set products2 = product2.Products

Set Nothing1 = products2.Item("setVis.2")

Set product2 = products1.Item("LaVisserie")

Set products2 = product2.Products

Set Nothing1 = products2.Item("setVis.2")

Set product2 = products1.Item("LaVisserie")

Set products2 = product2.Products

Set Nothing1 = products2.Item("setVis.2")

Set product2 = products1.Item("LaVisserie")

Set products2 = product2.Products

Set Nothing1 = products2.Item("setVis.2")

Set product2 = products1.Item("LaVisserie")

Set products2 = product2.Products

Set Nothing1 = products2.Item("setVis.2")

Set product2 = products1.Item("LaVisserie")

Set products2 = product2.Products

Set Nothing1 = products2.Item("setVis.2")

Set productDocument1 = CATIA.ActiveDocument

Set product1 = productDocument1.Product

Set products1 = product1.Products

Set productDocument1 = CATIA.ActiveDocument

Dim selection16 As Selection
Set selection16 = productDocument1.Selection

selection16.Search "Name=LaVisserie*,all"

Dim long14 As Long
long14 = selection16.Count

Set productDocument1 = CATIA.ActiveDocument

Set product1 = productDocument1.Product

Set products1 = product1.Products

Set product2 = products1.Item("LaVisserie")

Dim bSTR119 As String
bSTR119 = product2.DescriptionRef

Set productDocument1 = CATIA.ActiveDocument

Set selection16 = productDocument1.Selection

selection16.Clear

Dim arrayOfVariantOfBSTR28(0)
arrayOfVariantOfBSTR28(0) = "Publication"
Dim bSTR120 As String
Set selection16Variant = selection16
bSTR120 = selection16Variant.SelectElement2(arrayOfVariantOfBSTR28, "Selectionner l'axe du trou", False)

Dim selectedElement21 As SelectedElement
Set selectedElement21 = selection16.Item(1)

Dim publication24 As Publication
Set publication24 = selectedElement21.Value

Dim selectedElement22 As SelectedElement
Set selectedElement22 = selection16.Item(1)

Set publication24 = selectedElement22.Value

Dim publications13 As Publications
Set publications13 = product28.Publications

Set publication24 = publications13.Item("Axe")

Dim selectedElement23 As SelectedElement
Set selectedElement23 = selection16.Item(1)

Set publication24 = selectedElement23.Value

Set product28 = publications13.Parent

Dim bSTR121 As String
bSTR121 = product28.Name

Dim selectedElement24 As SelectedElement
Set selectedElement24 = selection16.Item(1)

Set publication24 = selectedElement24.Value

selection16.Clear

Set productDocument1 = CATIA.ActiveDocument

Set selection16 = productDocument1.Selection

selection16.Clear

Dim arrayOfVariantOfBSTR29(0)
arrayOfVariantOfBSTR29(0) = "Publication"
Dim bSTR122 As String
Set selection16Variant = selection16
bSTR122 = selection16Variant.SelectElement2(arrayOfVariantOfBSTR29, "Selectionner la face de contact de tête", False)

Dim selectedElement25 As SelectedElement
Set selectedElement25 = selection16.Item(1)

Dim publication25 As Publication
Set publication25 = selectedElement25.Value

Dim selectedElement26 As SelectedElement
Set selectedElement26 = selection16.Item(1)

Set publication25 = selectedElement26.Value

Set publication25 = publications13.Item("Face")

Dim selectedElement27 As SelectedElement
Set selectedElement27 = selection16.Item(1)

Set publication25 = selectedElement27.Value

Set product28 = publications13.Parent

Dim bSTR123 As String
bSTR123 = product28.Name

Dim selectedElement28 As SelectedElement
Set selectedElement28 = selection16.Item(1)

Set publication25 = selectedElement28.Value

selection16.Clear

Set productDocument1 = CATIA.ActiveDocument

Set selection16 = productDocument1.Selection

selection16.Clear

Dim arrayOfVariantOfBSTR30(0)
arrayOfVariantOfBSTR30(0) = "Publication"
Dim bSTR124 As String
Set selection16Variant = selection16
bSTR124 = selection16Variant.SelectElement2(arrayOfVariantOfBSTR30, "Selectionner la face de contact écrou", False)

Dim selectedElement29 As SelectedElement
Set selectedElement29 = selection16.Item(1)

Dim publication26 As Publication
Set publication26 = selectedElement29.Value

Dim selectedElement30 As SelectedElement
Set selectedElement30 = selection16.Item(1)

Set publication26 = selectedElement30.Value

Set publication26 = publications13.Item("Face1")

Dim selectedElement31 As SelectedElement
Set selectedElement31 = selection16.Item(1)

Set publication26 = selectedElement31.Value

Set product28 = publications13.Parent

Dim bSTR125 As String
bSTR125 = product28.Name

Dim selectedElement32 As SelectedElement
Set selectedElement32 = selection16.Item(1)

Set publication26 = selectedElement32.Value

Set productDocument1 = CATIA.ActiveDocument

Dim sPAWorkbench1 As SPAWorkbench
Set sPAWorkbench1 = productDocument1.GetWorkbench("SPAWorkbench")

Dim reference5 As Reference
' No resolution found for the object reference5...

Dim measurable1 As Measurable
Set measurable1 = sPAWorkbench1.GetMeasurable(reference5)

Dim reference6 As Reference
' No resolution found for the object reference6...

Dim double1 As Double
double1 = measurable1.GetMinimumDistance(reference6)

Dim reference7 As Reference
' No resolution found for the object reference7...

Dim double2 As Double
double2 = measurable1.GetMinimumDistance(reference7)

Dim measurable2 As Measurable
Set measurable2 = sPAWorkbench1.GetMeasurable(reference6)

Dim double3 As Double
double3 = measurable2.GetMinimumDistance(reference7)

selection16.Clear

Set productDocument1 = CATIA.ActiveDocument

Set product1 = productDocument1.Product

Set products1 = product1.Products

Set productDocument1 = CATIA.ActiveDocument

Set product1 = productDocument1.Product

Set products1 = product1.Products

Set product2 = products1.Item("LaVisserie")

Set products2 = product2.Products

Dim product29 As Product
Set product29 = products2.AddNewProduct("setVis")

Dim products15 As Products
Set products15 = product29.Products

Dim arrayOfVariantOfBSTR31(0)
arrayOfVariantOfBSTR31(0) = "D:\documents\Centrale Lyon\S8\PLM\insertion_vis\catalogue_vis_ecrou_rondelle\4x20CHC.CATPart"
Set products15Variant = products15
products15Variant.AddComponentsFromFiles arrayOfVariantOfBSTR31, "All"

Set products15 = product29.Products

Dim product30 As Product
Set product30 = products15.Item("4x20CHC.1")

Dim publications14 As Publications
Set publications14 = product30.Publications

Dim publication27 As Publication
Set publication27 = publications14.Item("FaceRondelle")

Set publications14 = product30.Publications

Dim publication28 As Publication
Set publication28 = publications14.Item("AxeVis")

Dim arrayOfVariantOfBSTR32(0)
arrayOfVariantOfBSTR32(0) = "D:\documents\Centrale Lyon\S8\PLM\insertion_vis\catalogue_vis_ecrou_rondelle\ecrou_M4_NS.CATPart"
Set products15Variant = products15
products15Variant.AddComponentsFromFiles arrayOfVariantOfBSTR32, "All"

Set products15 = product29.Products

Dim product31 As Product
Set product31 = products15.Item("ecrou_M4_NS.1")

Dim publications15 As Publications
Set publications15 = product31.Publications

Dim publication29 As Publication
Set publication29 = publications15.Item("FaceRondelle")

Set publications15 = product31.Publications

Dim publication30 As Publication
Set publication30 = publications15.Item("AxeVis")

Dim arrayOfVariantOfBSTR33(0)
arrayOfVariantOfBSTR33(0) = "D:\documents\Centrale Lyon\S8\PLM\insertion_vis\catalogue_vis_ecrou_rondelle\rondelle_M4.CATPart"
Set products15Variant = products15
products15Variant.AddComponentsFromFiles arrayOfVariantOfBSTR33, "All"

Set products15 = product29.Products

Dim product32 As Product
Set product32 = products15.Item("rondelle_M4.1")

Dim publications16 As Publications
Set publications16 = product32.Publications

Dim publication31 As Publication
Set publication31 = publications16.Item("FaceSup")

Set publications16 = product32.Publications

Dim publication32 As Publication
Set publication32 = publications16.Item("FaceInf")

Set publications16 = product32.Publications

Dim publication33 As Publication
Set publication33 = publications16.Item("AxeVis")

Dim arrayOfVariantOfBSTR34(0)
arrayOfVariantOfBSTR34(0) = "D:\documents\Centrale Lyon\S8\PLM\insertion_vis\catalogue_vis_ecrou_rondelle\rondelle_M4.CATPart"
Set products15Variant = products15
products15Variant.AddComponentsFromFiles arrayOfVariantOfBSTR34, "All"

Set products15 = product29.Products

Dim product33 As Product
Set product33 = products15.Item("rondelle_M4.2")

Dim publications17 As Publications
Set publications17 = product33.Publications

Dim publication34 As Publication
Set publication34 = publications17.Item("FaceSup")

Set publications17 = product33.Publications

Dim publication35 As Publication
Set publication35 = publications17.Item("FaceInf")

Set publications17 = product33.Publications

Dim publication36 As Publication
Set publication36 = publications17.Item("AxeVis")

Set productDocument1 = CATIA.ActiveDocument

Set selection16 = productDocument1.Selection

selection16.Clear

Dim bSTR126 As String
bSTR126 = product29.Name

Set products2 = product2.Products

Set product29 = products2.Item("setVis.3")

selection16.Add product29

CATIA.StartCommand "Flexible/rigide"

selection16.Clear

Set constraints1 = product1.Connections("CATIAConstraints")

Dim reference8 As Reference
' No resolution found for the object reference8...

Dim constraint6 As Constraint
Set constraint6 = constraints1.AddBiEltCst(catCstTypeOn, reference8, reference7)

Dim reference9 As Reference
' No resolution found for the object reference9...

Dim constraint7 As Constraint
Set constraint7 = constraints1.AddBiEltCst(catCstTypeOn, reference9, reference7)

Dim reference10 As Reference
' No resolution found for the object reference10...

Dim constraint8 As Constraint
Set constraint8 = constraints1.AddBiEltCst(catCstTypeOn, reference10, reference7)

Dim reference11 As Reference
' No resolution found for the object reference11...

Dim constraint9 As Constraint
Set constraint9 = constraints1.AddBiEltCst(catCstTypeOn, reference11, reference7)

Dim reference12 As Reference
' No resolution found for the object reference12...

Dim reference13 As Reference
' No resolution found for the object reference13...

Dim constraint10 As Constraint
Set constraint10 = constraints1.AddBiEltCst(catCstTypeSurfContact, reference12, reference13)

Dim reference14 As Reference
' No resolution found for the object reference14...

Dim constraint11 As Constraint
Set constraint11 = constraints1.AddBiEltCst(catCstTypeSurfContact, reference14, reference5)

Dim reference15 As Reference
' No resolution found for the object reference15...

Dim constraint12 As Constraint
Set constraint12 = constraints1.AddBiEltCst(catCstTypeSurfContact, reference6, reference15)

Dim reference16 As Reference
' No resolution found for the object reference16...

Dim reference17 As Reference
' No resolution found for the object reference17...

Dim constraint13 As Constraint
Set constraint13 = constraints1.AddBiEltCst(catCstTypeSurfContact, reference16, reference17)

Set productDocument1 = CATIA.ActiveDocument

Set selection16 = productDocument1.Selection

selection16.Clear

Dim bSTR127 As String
bSTR127 = constraint6.Name

Set constraint6 = constraints1.Item("Coïncidence.43")

selection16.Add constraint6

Dim bSTR128 As String
bSTR128 = constraint7.Name

Set constraint7 = constraints1.Item("Coïncidence.44")

selection16.Add constraint7

Dim bSTR129 As String
bSTR129 = constraint8.Name

Set constraint8 = constraints1.Item("Coïncidence.45")

selection16.Add constraint8

Dim bSTR130 As String
bSTR130 = constraint9.Name

Set constraint9 = constraints1.Item("Coïncidence.46")

selection16.Add constraint9

Dim bSTR131 As String
bSTR131 = constraint10.Name

Set constraint10 = constraints1.Item("Contact surfacique.47")

selection16.Add constraint10

Dim bSTR132 As String
bSTR132 = constraint11.Name

Set constraint11 = constraints1.Item("Contact surfacique.48")

selection16.Add constraint11

Dim bSTR133 As String
bSTR133 = constraint12.Name

Set constraint12 = constraints1.Item("Contact surfacique.49")

selection16.Add constraint12

Dim bSTR134 As String
bSTR134 = constraint13.Name

Set constraint13 = constraints1.Item("Contact surfacique.50")

selection16.Add constraint13

CATIA.StartCommand "Regrouper dans un nouveau groupe"

selection16.Clear

Set productDocument1 = CATIA.ActiveDocument

Set product1 = productDocument1.Product

product1.Update

Set productDocument1 = CATIA.ActiveDocument

Set selection16 = productDocument1.Selection

selection16.Clear

Dim arrayOfVariantOfBSTR35(0)
arrayOfVariantOfBSTR35(0) = "Part"
Dim bSTR135 As String
Set selection16Variant = selection16
bSTR135 = selection16Variant.SelectElement2(arrayOfVariantOfBSTR35, "Sélectionner un élément de la visserie", False)

Dim selectedElement33 As SelectedElement
Set selectedElement33 = selection16.Item(1)

Set product30 = selectedElement33.LeafProduct

Set products15 = product30.Parent

Set product29 = products15.Parent

Dim bSTR136 As String
bSTR136 = product29.PartNumber

Dim selectedElement34 As SelectedElement
Set selectedElement34 = selection16.Item(1)

Set product30 = selectedElement34.LeafProduct

Set products15 = product30.Parent

Set product29 = products15.Parent

Set products15 = product29.Products

Set product30 = products15.Item(1)

Set product31 = products15.Item(2)

Dim bSTR137 As String
bSTR137 = product30.PartNumber

Dim bSTR138 As String
bSTR138 = product30.PartNumber

selection16.Clear

Set products15 = product29.Products

Set product30 = products15.Item(1)

Set product31 = products15.Item(2)

Dim bSTR139 As String
bSTR139 = product30.PartNumber

Set productDocument1 = CATIA.ActiveDocument

Set product1 = productDocument1.Product

Set products1 = product1.Products

Set productDocument1 = CATIA.ActiveDocument

Set product1 = productDocument1.Product

Set products1 = product1.Products

Set product2 = products1.Item("LaVisserie")

Set products2 = product2.Products

Dim product34 As Product
Set product34 = products2.AddNewProduct("setOutil")

Dim products16 As Products
Set products16 = product34.Products

Dim arrayOfVariantOfBSTR36(0)
arrayOfVariantOfBSTR36(0) = "D:\documents\Centrale Lyon\S8\PLM\insertion_vis\catalogue_vis_ecrou_rondelle\outils\male_1,5.CATPart"
Set products16Variant = products16
products16Variant.AddComponentsFromFiles arrayOfVariantOfBSTR36, "All"

Set products16 = product34.Products

Dim product35 As Product
Set product35 = products16.Item("male_1,5.1")

Dim publications18 As Publications
Set publications18 = product35.Publications

Dim publication37 As Publication
Set publication37 = publications18.Item("Axe_grand")

Set publications18 = product35.Publications

Dim publication38 As Publication
Set publication38 = publications18.Item("Face_grand")

Dim arrayOfVariantOfBSTR37(0)
arrayOfVariantOfBSTR37(0) = "D:\documents\Centrale Lyon\S8\PLM\insertion_vis\catalogue_vis_ecrou_rondelle\outils\douille_4.CATPart"
Set products16Variant = products16
products16Variant.AddComponentsFromFiles arrayOfVariantOfBSTR37, "All"

Set products16 = product34.Products

Set Nothing1 = products16.Item("douille_4.1")

Set product2 = products1.Item("LaVisserie")

Set products2 = product2.Products

Set Nothing1 = products2.Item("setVis.2")

Set product2 = products1.Item("LaVisserie")

Set products2 = product2.Products

Set Nothing1 = products2.Item("setVis.2")

Set product2 = products1.Item("LaVisserie")

Set products2 = product2.Products

Set Nothing1 = products2.Item("setVis.2")

Set product2 = products1.Item("LaVisserie")

Set products2 = product2.Products

Set Nothing1 = products2.Item("setVis.2")

Set product2 = products1.Item("LaVisserie")

Set products2 = product2.Products

Set Nothing1 = products2.Item("setVis.2")

Set product2 = products1.Item("LaVisserie")

Set products2 = product2.Products

Set Nothing1 = products2.Item("setVis.2")

Set product2 = products1.Item("LaVisserie")

Set products2 = product2.Products

Set Nothing1 = products2.Item("setVis.2")

Set product2 = products1.Item("LaVisserie")

Set products2 = product2.Products

Set Nothing1 = products2.Item("setVis.2")

Set product2 = products1.Item("LaVisserie")

Set products2 = product2.Products

Set Nothing1 = products2.Item("setVis.2")

Set product2 = products1.Item("LaVisserie")

Set products2 = product2.Products

Set Nothing1 = products2.Item("setVis.2")

Set product2 = products1.Item("LaVisserie")

Set products2 = product2.Products

Set Nothing1 = products2.Item("setVis.2")

Set product2 = products1.Item("LaVisserie")

Set products2 = product2.Products

Set Nothing1 = products2.Item("setVis.2")

Set product2 = products1.Item("LaVisserie")

Set products2 = product2.Products

Set Nothing1 = products2.Item("setVis.2")

Set product2 = products1.Item("LaVisserie")

Set products2 = product2.Products

Set Nothing1 = products2.Item("setVis.2")

Set product2 = products1.Item("LaVisserie")

Set products2 = product2.Products

Set Nothing1 = products2.Item("setVis.2")

Set product2 = products1.Item("LaVisserie")

Set products2 = product2.Products

Set Nothing1 = products2.Item("setVis.2")

Set product2 = products1.Item("LaVisserie")

Set products2 = product2.Products

Set Nothing1 = products2.Item("setVis.2")

Set product2 = products1.Item("LaVisserie")

Set products2 = product2.Products

Set Nothing1 = products2.Item("setVis.2")

Set product2 = products1.Item("LaVisserie")

Set products2 = product2.Products

Set Nothing1 = products2.Item("setVis.2")

Set product2 = products1.Item("LaVisserie")

Set products2 = product2.Products

Set Nothing1 = products2.Item("setVis.2")

Set productDocument1 = CATIA.ActiveDocument

Dim selection17 As Selection
Set selection17 = productDocument1.Selection

selection17.Clear

selection17.Add product34

selection17.Delete

Set product2 = products1.Item("LaVisserie")

Set products2 = product2.Products

Set Nothing1 = products2.Item("setVis.2")

Set product2 = products1.Item("LaVisserie")

Set products2 = product2.Products

Set Nothing1 = products2.Item("setVis.2")

Set product2 = products1.Item("LaVisserie")

Set products2 = product2.Products

Set Nothing1 = products2.Item("setVis.2")

Set product2 = products1.Item("LaVisserie")

Set products2 = product2.Products

Set Nothing1 = products2.Item("setVis.2")

Set product2 = products1.Item("LaVisserie")

Set products2 = product2.Products

Set Nothing1 = products2.Item("setVis.2")

Set product2 = products1.Item("LaVisserie")

Set products2 = product2.Products

Set Nothing1 = products2.Item("setVis.2")

Set product2 = products1.Item("LaVisserie")

Set products2 = product2.Products

Set Nothing1 = products2.Item("setVis.2")

Set product2 = products1.Item("LaVisserie")

Set products2 = product2.Products

Set Nothing1 = products2.Item("setVis.2")

Set product2 = products1.Item("LaVisserie")

Set products2 = product2.Products

Set Nothing1 = products2.Item("setVis.2")

Set product2 = products1.Item("LaVisserie")

Set products2 = product2.Products

Set Nothing1 = products2.Item("setVis.2")

Set product2 = products1.Item("LaVisserie")

Set products2 = product2.Products

Set Nothing1 = products2.Item("setVis.2")

Set product2 = products1.Item("LaVisserie")

Set products2 = product2.Products

Set Nothing1 = products2.Item("setVis.2")

Set product2 = products1.Item("LaVisserie")

Set products2 = product2.Products

Set Nothing1 = products2.Item("setVis.2")

Set product2 = products1.Item("LaVisserie")

Set products2 = product2.Products

Set Nothing1 = products2.Item("setVis.2")

Set product2 = products1.Item("LaVisserie")

Set products2 = product2.Products

Set Nothing1 = products2.Item("setVis.2")

Set product2 = products1.Item("LaVisserie")

Set products2 = product2.Products

Set Nothing1 = products2.Item("setVis.2")

Set product2 = products1.Item("LaVisserie")

Set products2 = product2.Products

Set Nothing1 = products2.Item("setVis.2")

Set product2 = products1.Item("LaVisserie")

Set products2 = product2.Products

Set Nothing1 = products2.Item("setVis.2")

Set product2 = products1.Item("LaVisserie")

Set products2 = product2.Products

Set Nothing1 = products2.Item("setVis.2")

Set product2 = products1.Item("LaVisserie")

Set products2 = product2.Products

Set Nothing1 = products2.Item("setVis.2")

Set product2 = products1.Item("LaVisserie")

Set products2 = product2.Products

Set Nothing1 = products2.Item("setVis.2")

Set product2 = products1.Item("LaVisserie")

Set products2 = product2.Products

Set Nothing1 = products2.Item("setVis.2")

Set product2 = products1.Item("LaVisserie")

Set products2 = product2.Products

Set Nothing1 = products2.Item("setVis.2")

Set product2 = products1.Item("LaVisserie")

Set products2 = product2.Products

Set Nothing1 = products2.Item("setVis.2")

Set product2 = products1.Item("LaVisserie")

Set products2 = product2.Products

Set Nothing1 = products2.Item("setVis.2")

Set product2 = products1.Item("LaVisserie")

Set products2 = product2.Products

Set Nothing1 = products2.Item("setVis.2")

Set product2 = products1.Item("LaVisserie")

Set products2 = product2.Products

Set Nothing1 = products2.Item("setVis.2")

Set product2 = products1.Item("LaVisserie")

Set products2 = product2.Products

Set Nothing1 = products2.Item("setVis.2")

Set product2 = products1.Item("LaVisserie")

Set products2 = product2.Products

Set Nothing1 = products2.Item("setVis.2")

Set product2 = products1.Item("LaVisserie")

Set products2 = product2.Products

Set Nothing1 = products2.Item("setVis.2")

Set product2 = products1.Item("LaVisserie")

Set products2 = product2.Products

Set Nothing1 = products2.Item("setVis.2")

Set product2 = products1.Item("LaVisserie")

Set products2 = product2.Products

Set Nothing1 = products2.Item("setVis.2")

Set product2 = products1.Item("LaVisserie")

Set products2 = product2.Products

Set Nothing1 = products2.Item("setVis.2")

Set product2 = products1.Item("LaVisserie")

Set products2 = product2.Products

Set Nothing1 = products2.Item("setVis.2")

Set product2 = products1.Item("LaVisserie")

Set products2 = product2.Products

Set Nothing1 = products2.Item("setVis.2")

Set product2 = products1.Item("LaVisserie")

Set products2 = product2.Products

Set Nothing1 = products2.Item("setVis.2")

Set product2 = products1.Item("LaVisserie")

Set products2 = product2.Products

Set Nothing1 = products2.Item("setVis.2")

Set product2 = products1.Item("LaVisserie")

Set products2 = product2.Products

Set Nothing1 = products2.Item("setVis.2")

Set product2 = products1.Item("LaVisserie")

Set products2 = product2.Products

Set Nothing1 = products2.Item("setVis.2")

Set product2 = products1.Item("LaVisserie")

Set products2 = product2.Products

Set Nothing1 = products2.Item("setVis.2")

Set productDocument1 = CATIA.ActiveDocument

Dim selection18 As Selection
Set selection18 = productDocument1.Selection

selection18.Clear

selection18.Add product1

selection18.Delete

Set productDocument1 = CATIA.ActiveDocument

Dim selection19 As Selection
Set selection19 = productDocument1.Selection

selection19.Clear

selection19.Add product1

selection19.Delete

Set productDocument1 = CATIA.ActiveDocument

Dim selection20 As Selection
Set selection20 = productDocument1.Selection

selection20.Clear

selection20.Add product29

selection20.Delete

Set productDocument1 = CATIA.ActiveDocument

Set product1 = productDocument1.Product

Set products1 = product1.Products

Set productDocument1 = CATIA.ActiveDocument

Dim selection21 As Selection
Set selection21 = productDocument1.Selection

selection21.Search "Name=LaVisserie*,all"

Dim long15 As Long
long15 = selection21.Count

Set productDocument1 = CATIA.ActiveDocument

Set product1 = productDocument1.Product

Set products1 = product1.Products

Set product2 = products1.Item("LaVisserie")

Dim bSTR140 As String
bSTR140 = product2.DescriptionRef

Set productDocument1 = CATIA.ActiveDocument

Set selection21 = productDocument1.Selection

selection21.Clear

Dim arrayOfVariantOfBSTR38(0)
arrayOfVariantOfBSTR38(0) = "Publication"
Dim bSTR141 As String
Set selection21Variant = selection21
bSTR141 = selection21Variant.SelectElement2(arrayOfVariantOfBSTR38, "Selectionner l'axe du trou", False)

Dim selectedElement35 As SelectedElement
Set selectedElement35 = selection21.Item(1)

Set publication24 = selectedElement35.Value

Dim selectedElement36 As SelectedElement
Set selectedElement36 = selection21.Item(1)

Set publication24 = selectedElement36.Value

Set publication24 = publications13.Item("Axe")

Dim selectedElement37 As SelectedElement
Set selectedElement37 = selection21.Item(1)

Set publication24 = selectedElement37.Value

Set product28 = publications13.Parent

Dim bSTR142 As String
bSTR142 = product28.Name

Dim selectedElement38 As SelectedElement
Set selectedElement38 = selection21.Item(1)

Set publication24 = selectedElement38.Value

selection21.Clear

Set productDocument1 = CATIA.ActiveDocument

Set selection21 = productDocument1.Selection

selection21.Clear

Dim arrayOfVariantOfBSTR39(0)
arrayOfVariantOfBSTR39(0) = "Publication"
Dim bSTR143 As String
Set selection21Variant = selection21
bSTR143 = selection21Variant.SelectElement2(arrayOfVariantOfBSTR39, "Selectionner la face de contact de tête", False)

Dim selectedElement39 As SelectedElement
Set selectedElement39 = selection21.Item(1)

Set publication25 = selectedElement39.Value

Dim selectedElement40 As SelectedElement
Set selectedElement40 = selection21.Item(1)

Set publication25 = selectedElement40.Value

Set publication25 = publications13.Item("Face")

Dim selectedElement41 As SelectedElement
Set selectedElement41 = selection21.Item(1)

Set publication25 = selectedElement41.Value

Set product28 = publications13.Parent

Dim bSTR144 As String
bSTR144 = product28.Name

Dim selectedElement42 As SelectedElement
Set selectedElement42 = selection21.Item(1)

Set publication25 = selectedElement42.Value

selection21.Clear

Set productDocument1 = CATIA.ActiveDocument

Set selection21 = productDocument1.Selection

selection21.Clear

Dim arrayOfVariantOfBSTR40(0)
arrayOfVariantOfBSTR40(0) = "Publication"
Dim bSTR145 As String
Set selection21Variant = selection21
bSTR145 = selection21Variant.SelectElement2(arrayOfVariantOfBSTR40, "Selectionner la face de contact écrou", False)

Dim selectedElement43 As SelectedElement
Set selectedElement43 = selection21.Item(1)

Set publication26 = selectedElement43.Value

Dim selectedElement44 As SelectedElement
Set selectedElement44 = selection21.Item(1)

Set publication26 = selectedElement44.Value

Set publication26 = publications13.Item("Face1")

Dim selectedElement45 As SelectedElement
Set selectedElement45 = selection21.Item(1)

Set publication26 = selectedElement45.Value

Set product28 = publications13.Parent

Dim bSTR146 As String
bSTR146 = product28.Name

Dim selectedElement46 As SelectedElement
Set selectedElement46 = selection21.Item(1)

Set publication26 = selectedElement46.Value

Set productDocument1 = CATIA.ActiveDocument

Set sPAWorkbench1 = productDocument1.GetWorkbench("SPAWorkbench")

Dim measurable3 As Measurable
Set measurable3 = sPAWorkbench1.GetMeasurable(reference5)

Dim double4 As Double
double4 = measurable3.GetMinimumDistance(reference6)

Dim double5 As Double
double5 = measurable3.GetMinimumDistance(reference7)

Dim measurable4 As Measurable
Set measurable4 = sPAWorkbench1.GetMeasurable(reference6)

Dim double6 As Double
double6 = measurable4.GetMinimumDistance(reference7)

selection21.Clear

Set productDocument1 = CATIA.ActiveDocument

Set product1 = productDocument1.Product

Set products1 = product1.Products

Set productDocument1 = CATIA.ActiveDocument

Set product1 = productDocument1.Product

Set products1 = product1.Products

Set product2 = products1.Item("LaVisserie")

Set products2 = product2.Products

Dim product36 As Product
Set product36 = products2.AddNewProduct("setVis")

Dim products17 As Products
Set products17 = product36.Products

Dim arrayOfVariantOfBSTR41(0)
arrayOfVariantOfBSTR41(0) = "D:\documents\Centrale Lyon\S8\PLM\insertion_vis\catalogue_vis_ecrou_rondelle\4x20.CATPart"
Set products17Variant = products17
products17Variant.AddComponentsFromFiles arrayOfVariantOfBSTR41, "All"

Set products17 = product36.Products

Dim product37 As Product
Set product37 = products17.Item("4x20.1")

Dim publications19 As Publications
Set publications19 = product37.Publications

Dim publication39 As Publication
Set publication39 = publications19.Item("FaceRondelle")

Set publications19 = product37.Publications

Dim publication40 As Publication
Set publication40 = publications19.Item("AxeVis")

Dim arrayOfVariantOfBSTR42(0)
arrayOfVariantOfBSTR42(0) = "D:\documents\Centrale Lyon\S8\PLM\insertion_vis\catalogue_vis_ecrou_rondelle\ecrou_M4_NS.CATPart"
Set products17Variant = products17
products17Variant.AddComponentsFromFiles arrayOfVariantOfBSTR42, "All"

Set products17 = product36.Products

Dim product38 As Product
Set product38 = products17.Item("ecrou_M4_NS.1")

Dim publications20 As Publications
Set publications20 = product38.Publications

Dim publication41 As Publication
Set publication41 = publications20.Item("FaceRondelle")

Set publications20 = product38.Publications

Dim publication42 As Publication
Set publication42 = publications20.Item("AxeVis")

Dim arrayOfVariantOfBSTR43(0)
arrayOfVariantOfBSTR43(0) = "D:\documents\Centrale Lyon\S8\PLM\insertion_vis\catalogue_vis_ecrou_rondelle\rondelle_M4.CATPart"
Set products17Variant = products17
products17Variant.AddComponentsFromFiles arrayOfVariantOfBSTR43, "All"

Set products17 = product36.Products

Dim product39 As Product
Set product39 = products17.Item("rondelle_M4.1")

Dim publications21 As Publications
Set publications21 = product39.Publications

Dim publication43 As Publication
Set publication43 = publications21.Item("FaceSup")

Set publications21 = product39.Publications

Dim publication44 As Publication
Set publication44 = publications21.Item("FaceInf")

Set publications21 = product39.Publications

Dim publication45 As Publication
Set publication45 = publications21.Item("AxeVis")

Dim arrayOfVariantOfBSTR44(0)
arrayOfVariantOfBSTR44(0) = "D:\documents\Centrale Lyon\S8\PLM\insertion_vis\catalogue_vis_ecrou_rondelle\rondelle_M4.CATPart"
Set products17Variant = products17
products17Variant.AddComponentsFromFiles arrayOfVariantOfBSTR44, "All"

Set products17 = product36.Products

Dim product40 As Product
Set product40 = products17.Item("rondelle_M4.2")

Dim publications22 As Publications
Set publications22 = product40.Publications

Dim publication46 As Publication
Set publication46 = publications22.Item("FaceSup")

Set publications22 = product40.Publications

Dim publication47 As Publication
Set publication47 = publications22.Item("FaceInf")

Set publications22 = product40.Publications

Dim publication48 As Publication
Set publication48 = publications22.Item("AxeVis")

Set productDocument1 = CATIA.ActiveDocument

Set selection21 = productDocument1.Selection

selection21.Clear

Dim bSTR147 As String
bSTR147 = product36.Name

Set products2 = product2.Products

Set product36 = products2.Item("setVis.4")

selection21.Add product36

CATIA.StartCommand "Flexible/rigide"

selection21.Clear

Set constraints1 = product1.Connections("CATIAConstraints")

Dim reference18 As Reference
' No resolution found for the object reference18...

Dim constraint14 As Constraint
Set constraint14 = constraints1.AddBiEltCst(catCstTypeOn, reference18, reference7)

Dim reference19 As Reference
' No resolution found for the object reference19...

Dim constraint15 As Constraint
Set constraint15 = constraints1.AddBiEltCst(catCstTypeOn, reference19, reference7)

Dim reference20 As Reference
' No resolution found for the object reference20...

Dim constraint16 As Constraint
Set constraint16 = constraints1.AddBiEltCst(catCstTypeOn, reference20, reference7)

Dim reference21 As Reference
' No resolution found for the object reference21...

Dim constraint17 As Constraint
Set constraint17 = constraints1.AddBiEltCst(catCstTypeOn, reference21, reference7)

Dim reference22 As Reference
' No resolution found for the object reference22...

Dim reference23 As Reference
' No resolution found for the object reference23...

Dim constraint18 As Constraint
Set constraint18 = constraints1.AddBiEltCst(catCstTypeSurfContact, reference22, reference23)

Dim reference24 As Reference
' No resolution found for the object reference24...

Dim constraint19 As Constraint
Set constraint19 = constraints1.AddBiEltCst(catCstTypeSurfContact, reference24, reference5)

Dim reference25 As Reference
' No resolution found for the object reference25...

Dim constraint20 As Constraint
Set constraint20 = constraints1.AddBiEltCst(catCstTypeSurfContact, reference6, reference25)

Dim reference26 As Reference
' No resolution found for the object reference26...

Dim reference27 As Reference
' No resolution found for the object reference27...

Dim constraint21 As Constraint
Set constraint21 = constraints1.AddBiEltCst(catCstTypeSurfContact, reference26, reference27)

Set productDocument1 = CATIA.ActiveDocument

Set selection21 = productDocument1.Selection

selection21.Clear

Dim bSTR148 As String
bSTR148 = constraint14.Name

Set constraint14 = constraints1.Item("Coïncidence.51")

selection21.Add constraint14

Dim bSTR149 As String
bSTR149 = constraint15.Name

Set constraint15 = constraints1.Item("Coïncidence.52")

selection21.Add constraint15

Dim bSTR150 As String
bSTR150 = constraint16.Name

Set constraint16 = constraints1.Item("Coïncidence.53")

selection21.Add constraint16

Dim bSTR151 As String
bSTR151 = constraint17.Name

Set constraint17 = constraints1.Item("Coïncidence.54")

selection21.Add constraint17

Dim bSTR152 As String
bSTR152 = constraint18.Name

Set constraint18 = constraints1.Item("Contact surfacique.55")

selection21.Add constraint18

Dim bSTR153 As String
bSTR153 = constraint19.Name

Set constraint19 = constraints1.Item("Contact surfacique.56")

selection21.Add constraint19

Dim bSTR154 As String
bSTR154 = constraint20.Name

Set constraint20 = constraints1.Item("Contact surfacique.57")

selection21.Add constraint20

Dim bSTR155 As String
bSTR155 = constraint21.Name

Set constraint21 = constraints1.Item("Contact surfacique.58")

selection21.Add constraint21

CATIA.StartCommand "Regrouper dans un nouveau groupe"

selection21.Clear

Set productDocument1 = CATIA.ActiveDocument

Set product1 = productDocument1.Product

product1.Update

Set productDocument1 = CATIA.ActiveDocument

Set selection21 = productDocument1.Selection

selection21.Clear

Dim arrayOfVariantOfBSTR45(0)
arrayOfVariantOfBSTR45(0) = "Part"
Dim bSTR156 As String
Set selection21Variant = selection21
bSTR156 = selection21Variant.SelectElement2(arrayOfVariantOfBSTR45, "Sélectionner un élément de la visserie", False)

Dim selectedElement47 As SelectedElement
Set selectedElement47 = selection21.Item(1)

Set product37 = selectedElement47.LeafProduct

Set products17 = product37.Parent

Set product36 = products17.Parent

Dim bSTR157 As String
bSTR157 = product36.PartNumber

Dim selectedElement48 As SelectedElement
Set selectedElement48 = selection21.Item(1)

Set product37 = selectedElement48.LeafProduct

Set products17 = product37.Parent

Set product36 = products17.Parent

Set products17 = product36.Products

Set product37 = products17.Item(1)

Set product38 = products17.Item(2)

Dim bSTR158 As String
bSTR158 = product37.PartNumber

Dim bSTR159 As String
bSTR159 = product37.PartNumber

selection21.Clear

Set products17 = product36.Products

Set product37 = products17.Item(1)

Set product38 = products17.Item(2)

Dim bSTR160 As String
bSTR160 = product37.PartNumber

Set productDocument1 = CATIA.ActiveDocument

Set product1 = productDocument1.Product

Set products1 = product1.Products

Set productDocument1 = CATIA.ActiveDocument

Set product1 = productDocument1.Product

Set products1 = product1.Products

Set product2 = products1.Item("LaVisserie")

Set products2 = product2.Products

Dim product41 As Product
Set product41 = products2.AddNewProduct("setOutil")

Dim products18 As Products
Set products18 = product41.Products

Dim arrayOfVariantOfBSTR46(0)
arrayOfVariantOfBSTR46(0) = "D:\documents\Centrale Lyon\S8\PLM\insertion_vis\catalogue_vis_ecrou_rondelle\outils\_4.CATPart"
Set products18Variant = products18
products18Variant.AddComponentsFromFiles arrayOfVariantOfBSTR46, "All"

Set products18 = product41.Products

Set Nothing1 = products18.Item("_4.1")

Set productDocument1 = CATIA.ActiveDocument

Dim selection22 As Selection
Set selection22 = productDocument1.Selection

selection22.Clear

selection22.Add product41

selection22.Delete

Set productDocument1 = CATIA.ActiveDocument

Set product1 = productDocument1.Product

Set products1 = product1.Products

Set productDocument1 = CATIA.ActiveDocument

Dim selection23 As Selection
Set selection23 = productDocument1.Selection

selection23.Search "Name=LaVisserie*,all"

Dim long16 As Long
long16 = selection23.Count

Set productDocument1 = CATIA.ActiveDocument

Set product1 = productDocument1.Product

Set products1 = product1.Products

Set product2 = products1.Item("LaVisserie")

Dim bSTR161 As String
bSTR161 = product2.DescriptionRef

Set productDocument1 = CATIA.ActiveDocument

Set selection23 = productDocument1.Selection

selection23.Clear

Dim arrayOfVariantOfBSTR47(0)
arrayOfVariantOfBSTR47(0) = "Part"
Dim bSTR162 As String
Set selection23Variant = selection23
bSTR162 = selection23Variant.SelectElement2(arrayOfVariantOfBSTR47, "Sélectionner un élément de la visserie", False)

Dim selectedElement49 As SelectedElement
Set selectedElement49 = selection23.Item(1)

Set product37 = selectedElement49.LeafProduct

Set products17 = product37.Parent

Set product36 = products17.Parent

Dim bSTR163 As String
bSTR163 = product36.PartNumber

Dim selectedElement50 As SelectedElement
Set selectedElement50 = selection23.Item(1)

Set product37 = selectedElement50.LeafProduct

Set products17 = product37.Parent

Set product36 = products17.Parent

Set products17 = product36.Products

Set product37 = products17.Item(1)

Set product38 = products17.Item(2)

Dim bSTR164 As String
bSTR164 = product37.PartNumber

Dim bSTR165 As String
bSTR165 = product37.PartNumber

selection23.Clear

Set products17 = product36.Products

Set product37 = products17.Item(1)

Set product38 = products17.Item(2)

Dim bSTR166 As String
bSTR166 = product37.PartNumber

Set productDocument1 = CATIA.ActiveDocument

Set product1 = productDocument1.Product

Set products1 = product1.Products

Set productDocument1 = CATIA.ActiveDocument

Set product1 = productDocument1.Product

Set products1 = product1.Products

Set product2 = products1.Item("LaVisserie")

Set products2 = product2.Products

Dim product42 As Product
Set product42 = products2.AddNewProduct("setOutil")

Dim products19 As Products
Set products19 = product42.Products

Dim arrayOfVariantOfBSTR48(0)
arrayOfVariantOfBSTR48(0) = "D:\documents\Centrale Lyon\S8\PLM\insertion_vis\catalogue_vis_ecrou_rondelle\outils\_4.CATPart"
Set products19Variant = products19
products19Variant.AddComponentsFromFiles arrayOfVariantOfBSTR48, "All"

Set products19 = product42.Products

Set Nothing1 = products19.Item("_4.1")

Set productDocument1 = CATIA.ActiveDocument

Dim selection24 As Selection
Set selection24 = productDocument1.Selection

selection24.Clear

selection24.Add product42

selection24.Delete

Set productDocument1 = CATIA.ActiveDocument

Set product1 = productDocument1.Product

Set products1 = product1.Products

Set productDocument1 = CATIA.ActiveDocument

Dim selection25 As Selection
Set selection25 = productDocument1.Selection

selection25.Search "Name=LaVisserie*,all"

Dim long17 As Long
long17 = selection25.Count

Set productDocument1 = CATIA.ActiveDocument

Set product1 = productDocument1.Product

Set products1 = product1.Products

Set product2 = products1.Item("LaVisserie")

Dim bSTR167 As String
bSTR167 = product2.DescriptionRef

Set productDocument1 = CATIA.ActiveDocument

Set selection25 = productDocument1.Selection

selection25.Clear

Dim arrayOfVariantOfBSTR49(0)
arrayOfVariantOfBSTR49(0) = "Part"
Dim bSTR168 As String
Set selection25Variant = selection25
bSTR168 = selection25Variant.SelectElement2(arrayOfVariantOfBSTR49, "Sélectionner un élément de la visserie", False)

Dim selectedElement51 As SelectedElement
Set selectedElement51 = selection25.Item(1)

Set product37 = selectedElement51.LeafProduct

Set products17 = product37.Parent

Set product36 = products17.Parent

Dim bSTR169 As String
bSTR169 = product36.PartNumber

Dim selectedElement52 As SelectedElement
Set selectedElement52 = selection25.Item(1)

Set product37 = selectedElement52.LeafProduct

Set products17 = product37.Parent

Set product36 = products17.Parent

Set products17 = product36.Products

Set product37 = products17.Item(1)

Set product38 = products17.Item(2)

Dim bSTR170 As String
bSTR170 = product37.PartNumber

Dim bSTR171 As String
bSTR171 = product37.PartNumber

selection25.Clear

Set products17 = product36.Products

Set product37 = products17.Item(1)

Set product38 = products17.Item(2)

Dim bSTR172 As String
bSTR172 = product37.PartNumber

Set productDocument1 = CATIA.ActiveDocument

Set product1 = productDocument1.Product

Set products1 = product1.Products

Set productDocument1 = CATIA.ActiveDocument

Set product1 = productDocument1.Product

Set products1 = product1.Products

Set product2 = products1.Item("LaVisserie")

Set products2 = product2.Products

Dim product43 As Product
Set product43 = products2.AddNewProduct("setOutil")

Dim products20 As Products
Set products20 = product43.Products

Dim arrayOfVariantOfBSTR50(0)
arrayOfVariantOfBSTR50(0) = "D:\documents\Centrale Lyon\S8\PLM\insertion_vis\catalogue_vis_ecrou_rondelle\outils\_4.CATPart"
Set products20Variant = products20
products20Variant.AddComponentsFromFiles arrayOfVariantOfBSTR50, "All"

Set products20 = product43.Products

Set Nothing1 = products20.Item("_4.1")

Set products20 = product43.Products

Set Nothing1 = products20.Item("_4.1")

Set productDocument1 = CATIA.ActiveDocument

Set product1 = productDocument1.Product

Set products1 = product1.Products

Set productDocument1 = CATIA.ActiveDocument

Dim selection26 As Selection
Set selection26 = productDocument1.Selection

selection26.Search "Name=LaVisserie*,all"

Dim long18 As Long
long18 = selection26.Count

Set productDocument1 = CATIA.ActiveDocument

Set product1 = productDocument1.Product

Set products1 = product1.Products

Set product2 = products1.Item("LaVisserie")

Dim bSTR173 As String
bSTR173 = product2.DescriptionRef

Set productDocument1 = CATIA.ActiveDocument

Set selection26 = productDocument1.Selection

selection26.Clear

Dim arrayOfVariantOfBSTR51(0)
arrayOfVariantOfBSTR51(0) = "Part"
Dim bSTR174 As String
Set selection26Variant = selection26
bSTR174 = selection26Variant.SelectElement2(arrayOfVariantOfBSTR51, "Sélectionner un élément de la visserie", False)

Dim selectedElement53 As SelectedElement
Set selectedElement53 = selection26.Item(1)

Set product37 = selectedElement53.LeafProduct

Set products17 = product37.Parent

Set product36 = products17.Parent

Dim bSTR175 As String
bSTR175 = product36.PartNumber

Dim selectedElement54 As SelectedElement
Set selectedElement54 = selection26.Item(1)

Set product37 = selectedElement54.LeafProduct

Set products17 = product37.Parent

Set product36 = products17.Parent

Set products17 = product36.Products

Set product37 = products17.Item(1)

Set product38 = products17.Item(2)

Dim bSTR176 As String
bSTR176 = product37.PartNumber

Dim bSTR177 As String
bSTR177 = product37.PartNumber

selection26.Clear

Set products17 = product36.Products

Set product37 = products17.Item(1)

Set product38 = products17.Item(2)

Dim bSTR178 As String
bSTR178 = product37.PartNumber

Set productDocument1 = CATIA.ActiveDocument

Set product1 = productDocument1.Product

Set products1 = product1.Products

Set productDocument1 = CATIA.ActiveDocument

Set product1 = productDocument1.Product

Set products1 = product1.Products

Set product2 = products1.Item("LaVisserie")

Set products2 = product2.Products

Dim product44 As Product
Set product44 = products2.AddNewProduct("setOutil")

Dim products21 As Products
Set products21 = product44.Products

Dim arrayOfVariantOfBSTR52(0)
arrayOfVariantOfBSTR52(0) = "D:\documents\Centrale Lyon\S8\PLM\insertion_vis\catalogue_vis_ecrou_rondelle\outils\_4.CATPart"
Set products21Variant = products21
products21Variant.AddComponentsFromFiles arrayOfVariantOfBSTR52, "All"

Set products21 = product44.Products

Set Nothing1 = products21.Item("_4.1")

Set productDocument1 = CATIA.ActiveDocument

Set product1 = productDocument1.Product

Set products1 = product1.Products

Set productDocument1 = CATIA.ActiveDocument

Dim selection27 As Selection
Set selection27 = productDocument1.Selection

selection27.Search "Name=LaVisserie*,all"

Dim long19 As Long
long19 = selection27.Count

Set productDocument1 = CATIA.ActiveDocument

Set product1 = productDocument1.Product

Set products1 = product1.Products

Set product2 = products1.Item("LaVisserie")

Dim bSTR179 As String
bSTR179 = product2.DescriptionRef

Set productDocument1 = CATIA.ActiveDocument

Set selection27 = productDocument1.Selection

selection27.Clear

Dim arrayOfVariantOfBSTR53(0)
arrayOfVariantOfBSTR53(0) = "Part"
Dim bSTR180 As String
Set selection27Variant = selection27
bSTR180 = selection27Variant.SelectElement2(arrayOfVariantOfBSTR53, "Sélectionner un élément de la visserie", False)

Dim selectedElement55 As SelectedElement
Set selectedElement55 = selection27.Item(1)

Set product37 = selectedElement55.LeafProduct

Set products17 = product37.Parent

Set product36 = products17.Parent

Dim bSTR181 As String
bSTR181 = product36.PartNumber

Dim selectedElement56 As SelectedElement
Set selectedElement56 = selection27.Item(1)

Set product37 = selectedElement56.LeafProduct

Set products17 = product37.Parent

Set product36 = products17.Parent

Set products17 = product36.Products

Set product37 = products17.Item(1)

Set product38 = products17.Item(2)

Dim bSTR182 As String
bSTR182 = product37.PartNumber

Dim bSTR183 As String
bSTR183 = product37.PartNumber

selection27.Clear

Set productDocument1 = CATIA.ActiveDocument

Set product1 = productDocument1.Product

Set products1 = product1.Products

Set productDocument1 = CATIA.ActiveDocument

Dim selection28 As Selection
Set selection28 = productDocument1.Selection

selection28.Search "Name=LaVisserie*,all"

Dim long20 As Long
long20 = selection28.Count

Set productDocument1 = CATIA.ActiveDocument

Set product1 = productDocument1.Product

Set products1 = product1.Products

Set product2 = products1.Item("LaVisserie")

Dim bSTR184 As String
bSTR184 = product2.DescriptionRef

Set productDocument1 = CATIA.ActiveDocument

Set selection28 = productDocument1.Selection

selection28.Clear

Dim arrayOfVariantOfBSTR54(0)
arrayOfVariantOfBSTR54(0) = "Part"
Dim bSTR185 As String
Set selection28Variant = selection28
bSTR185 = selection28Variant.SelectElement2(arrayOfVariantOfBSTR54, "Sélectionner un élément de la visserie", False)

Dim selectedElement57 As SelectedElement
Set selectedElement57 = selection28.Item(1)

Set product37 = selectedElement57.LeafProduct

Set products17 = product37.Parent

Set product36 = products17.Parent

Dim bSTR186 As String
bSTR186 = product36.PartNumber

Dim selectedElement58 As SelectedElement
Set selectedElement58 = selection28.Item(1)

Set product37 = selectedElement58.LeafProduct

Set products17 = product37.Parent

Set product36 = products17.Parent

Set products17 = product36.Products

Set product37 = products17.Item(1)

Set product38 = products17.Item(2)

Dim bSTR187 As String
bSTR187 = product37.PartNumber

Dim bSTR188 As String
bSTR188 = product37.PartNumber

selection28.Clear

Set productDocument1 = CATIA.ActiveDocument

Set product1 = productDocument1.Product

Set products1 = product1.Products

Set productDocument1 = CATIA.ActiveDocument

Dim selection29 As Selection
Set selection29 = productDocument1.Selection

selection29.Search "Name=LaVisserie*,all"

Dim long21 As Long
long21 = selection29.Count

Set productDocument1 = CATIA.ActiveDocument

Set product1 = productDocument1.Product

Set products1 = product1.Products

Set product2 = products1.Item("LaVisserie")

Dim bSTR189 As String
bSTR189 = product2.DescriptionRef

Set productDocument1 = CATIA.ActiveDocument

Set selection29 = productDocument1.Selection

selection29.Clear

Dim arrayOfVariantOfBSTR55(0)
arrayOfVariantOfBSTR55(0) = "Part"
Dim bSTR190 As String
Set selection29Variant = selection29
bSTR190 = selection29Variant.SelectElement2(arrayOfVariantOfBSTR55, "Sélectionner un élément de la visserie", False)

Dim selectedElement59 As SelectedElement
Set selectedElement59 = selection29.Item(1)

Set product37 = selectedElement59.LeafProduct

Set products17 = product37.Parent

Set product36 = products17.Parent

Dim bSTR191 As String
bSTR191 = product36.PartNumber

Dim selectedElement60 As SelectedElement
Set selectedElement60 = selection29.Item(1)

Set product37 = selectedElement60.LeafProduct

Set products17 = product37.Parent

Set product36 = products17.Parent

Set products17 = product36.Products

Set product37 = products17.Item(1)

Set product38 = products17.Item(2)

Dim bSTR192 As String
bSTR192 = product37.PartNumber

Dim bSTR193 As String
bSTR193 = product37.PartNumber

selection29.Clear

Set products17 = product36.Products

Set product37 = products17.Item(1)

Set product38 = products17.Item(2)

Dim bSTR194 As String
bSTR194 = product37.PartNumber

Set productDocument1 = CATIA.ActiveDocument

Set product1 = productDocument1.Product

Set products1 = product1.Products

Set productDocument1 = CATIA.ActiveDocument

Set product1 = productDocument1.Product

Set products1 = product1.Products

Set product2 = products1.Item("LaVisserie")

Set products2 = product2.Products

Dim product45 As Product
Set product45 = products2.AddNewProduct("setOutil")

Dim products22 As Products
Set products22 = product45.Products

Dim arrayOfVariantOfBSTR56(0)
arrayOfVariantOfBSTR56(0) = "D:\documents\Centrale Lyon\S8\PLM\insertion_vis\catalogue_vis_ecrou_rondelle\outils\_4.CATPart"
Set products22Variant = products22
products22Variant.AddComponentsFromFiles arrayOfVariantOfBSTR56, "All"

Set products22 = product45.Products

Set Nothing1 = products22.Item("_4.1")

Set productDocument1 = CATIA.ActiveDocument

Set product1 = productDocument1.Product

Set products1 = product1.Products

Set productDocument1 = CATIA.ActiveDocument

Dim selection30 As Selection
Set selection30 = productDocument1.Selection

selection30.Search "Name=LaVisserie*,all"

Dim long22 As Long
long22 = selection30.Count

Set productDocument1 = CATIA.ActiveDocument

Set product1 = productDocument1.Product

Set products1 = product1.Products

Set product2 = products1.Item("LaVisserie")

Dim bSTR195 As String
bSTR195 = product2.DescriptionRef

Set productDocument1 = CATIA.ActiveDocument

Set selection30 = productDocument1.Selection

selection30.Clear

Dim arrayOfVariantOfBSTR57(0)
arrayOfVariantOfBSTR57(0) = "Part"
Dim bSTR196 As String
Set selection30Variant = selection30
bSTR196 = selection30Variant.SelectElement2(arrayOfVariantOfBSTR57, "Sélectionner un élément de la visserie", False)

Dim selectedElement61 As SelectedElement
Set selectedElement61 = selection30.Item(1)

Set product37 = selectedElement61.LeafProduct

Set products17 = product37.Parent

Set product36 = products17.Parent

Dim bSTR197 As String
bSTR197 = product36.PartNumber

Dim selectedElement62 As SelectedElement
Set selectedElement62 = selection30.Item(1)

Set product37 = selectedElement62.LeafProduct

Set products17 = product37.Parent

Set product36 = products17.Parent

Set products17 = product36.Products

Set product37 = products17.Item(1)

Set product38 = products17.Item(2)

Dim bSTR198 As String
bSTR198 = product37.PartNumber

Dim bSTR199 As String
bSTR199 = product37.PartNumber

selection30.Clear

Set products17 = product36.Products

Set product37 = products17.Item(1)

Set product38 = products17.Item(2)

Dim bSTR200 As String
bSTR200 = product37.PartNumber

Set productDocument1 = CATIA.ActiveDocument

Set product1 = productDocument1.Product

Set products1 = product1.Products

Set productDocument1 = CATIA.ActiveDocument

Set product1 = productDocument1.Product

Set products1 = product1.Products

Set product2 = products1.Item("LaVisserie")

Set products2 = product2.Products

Dim product46 As Product
Set product46 = products2.AddNewProduct("setOutil")

Dim products23 As Products
Set products23 = product46.Products

Dim arrayOfVariantOfBSTR58(0)
arrayOfVariantOfBSTR58(0) = "D:\documents\Centrale Lyon\S8\PLM\insertion_vis\catalogue_vis_ecrou_rondelle\outils\_4.CATPart"
Set products23Variant = products23
products23Variant.AddComponentsFromFiles arrayOfVariantOfBSTR58, "All"

Set products23 = product46.Products

Set Nothing1 = products23.Item("_4.1")

Set productDocument1 = CATIA.ActiveDocument

Set product1 = productDocument1.Product

Set products1 = product1.Products

Set productDocument1 = CATIA.ActiveDocument

Dim selection31 As Selection
Set selection31 = productDocument1.Selection

selection31.Search "Name=LaVisserie*,all"

Dim long23 As Long
long23 = selection31.Count

Set productDocument1 = CATIA.ActiveDocument

Set product1 = productDocument1.Product

Set products1 = product1.Products

Set product2 = products1.Item("LaVisserie")

Dim bSTR201 As String
bSTR201 = product2.DescriptionRef

Set productDocument1 = CATIA.ActiveDocument

Set selection31 = productDocument1.Selection

selection31.Clear

Dim arrayOfVariantOfBSTR59(0)
arrayOfVariantOfBSTR59(0) = "Part"
Dim bSTR202 As String
Set selection31Variant = selection31
bSTR202 = selection31Variant.SelectElement2(arrayOfVariantOfBSTR59, "Sélectionner un élément de la visserie", False)

Dim selectedElement63 As SelectedElement
Set selectedElement63 = selection31.Item(1)

Set product37 = selectedElement63.LeafProduct

Set products17 = product37.Parent

Set product36 = products17.Parent

Dim bSTR203 As String
bSTR203 = product36.PartNumber

Dim selectedElement64 As SelectedElement
Set selectedElement64 = selection31.Item(1)

Set product37 = selectedElement64.LeafProduct

Set products17 = product37.Parent

Set product36 = products17.Parent

Set products17 = product36.Products

Set product37 = products17.Item(1)

Set product38 = products17.Item(2)

Dim bSTR204 As String
bSTR204 = product37.PartNumber

Dim bSTR205 As String
bSTR205 = product37.PartNumber

selection31.Clear

Set products17 = product36.Products

Set product37 = products17.Item(1)

Set product38 = products17.Item(2)

Dim bSTR206 As String
bSTR206 = product37.PartNumber

Set productDocument1 = CATIA.ActiveDocument

Set product1 = productDocument1.Product

Set products1 = product1.Products

Set productDocument1 = CATIA.ActiveDocument

Set product1 = productDocument1.Product

Set products1 = product1.Products

Set product2 = products1.Item("LaVisserie")

Set products2 = product2.Products

Dim product47 As Product
Set product47 = products2.AddNewProduct("setOutil")

Dim products24 As Products
Set products24 = product47.Products

Dim arrayOfVariantOfBSTR60(0)
arrayOfVariantOfBSTR60(0) = "D:\documents\Centrale Lyon\S8\PLM\insertion_vis\catalogue_vis_ecrou_rondelle\outils\_4.CATPart"
Set products24Variant = products24
products24Variant.AddComponentsFromFiles arrayOfVariantOfBSTR60, "All"

Set products24 = product47.Products

Set Nothing1 = products24.Item("_4.1")

Set productDocument1 = CATIA.ActiveDocument

Set product1 = productDocument1.Product

Set products1 = product1.Products

Set productDocument1 = CATIA.ActiveDocument

Dim selection32 As Selection
Set selection32 = productDocument1.Selection

selection32.Search "Name=LaVisserie*,all"

Dim long24 As Long
long24 = selection32.Count

Set productDocument1 = CATIA.ActiveDocument

Set product1 = productDocument1.Product

Set products1 = product1.Products

Set product2 = products1.Item("LaVisserie")

Dim bSTR207 As String
bSTR207 = product2.DescriptionRef

Set productDocument1 = CATIA.ActiveDocument

Set selection32 = productDocument1.Selection

selection32.Clear

Dim arrayOfVariantOfBSTR61(0)
arrayOfVariantOfBSTR61(0) = "Part"
Dim bSTR208 As String
Set selection32Variant = selection32
bSTR208 = selection32Variant.SelectElement2(arrayOfVariantOfBSTR61, "Sélectionner un élément de la visserie", False)

Dim selectedElement65 As SelectedElement
Set selectedElement65 = selection32.Item(1)

Set product37 = selectedElement65.LeafProduct

Set products17 = product37.Parent

Set product36 = products17.Parent

Dim bSTR209 As String
bSTR209 = product36.PartNumber

Dim selectedElement66 As SelectedElement
Set selectedElement66 = selection32.Item(1)

Set product37 = selectedElement66.LeafProduct

Set products17 = product37.Parent

Set product36 = products17.Parent

Set products17 = product36.Products

Set product37 = products17.Item(1)

Set product38 = products17.Item(2)

Dim bSTR210 As String
bSTR210 = product37.PartNumber

Dim bSTR211 As String
bSTR211 = product37.PartNumber

selection32.Clear

Set products17 = product36.Products

Set product37 = products17.Item(1)

Set product38 = products17.Item(2)

Dim bSTR212 As String
bSTR212 = product37.PartNumber

Set productDocument1 = CATIA.ActiveDocument

Set product1 = productDocument1.Product

Set products1 = product1.Products

Set productDocument1 = CATIA.ActiveDocument

Set product1 = productDocument1.Product

Set products1 = product1.Products

Set product2 = products1.Item("LaVisserie")

Set products2 = product2.Products

Dim product48 As Product
Set product48 = products2.AddNewProduct("setOutil")

Dim products25 As Products
Set products25 = product48.Products

Dim arrayOfVariantOfBSTR62(0)
arrayOfVariantOfBSTR62(0) = "D:\documents\Centrale Lyon\S8\PLM\insertion_vis\catalogue_vis_ecrou_rondelle\outils\_4.CATPart"
Set products25Variant = products25
products25Variant.AddComponentsFromFiles arrayOfVariantOfBSTR62, "All"

Set products25 = product48.Products

Set Nothing1 = products25.Item("_4.1")

Set productDocument1 = CATIA.ActiveDocument

Dim selection33 As Selection
Set selection33 = productDocument1.Selection

selection33.Clear

selection33.Add product43

selection33.Add product44

selection33.Add product45

selection33.Add product46

selection33.Add product47

selection33.Add product48

selection33.Delete

Set productDocument1 = CATIA.ActiveDocument

Set product1 = productDocument1.Product

Set products1 = product1.Products

Set productDocument1 = CATIA.ActiveDocument

Dim selection34 As Selection
Set selection34 = productDocument1.Selection

selection34.Search "Name=LaVisserie*,all"

Dim long25 As Long
long25 = selection34.Count

Set productDocument1 = CATIA.ActiveDocument

Set product1 = productDocument1.Product

Set products1 = product1.Products

Set product2 = products1.Item("LaVisserie")

Dim bSTR213 As String
bSTR213 = product2.DescriptionRef

Set productDocument1 = CATIA.ActiveDocument

Set selection34 = productDocument1.Selection

selection34.Clear

Dim arrayOfVariantOfBSTR63(0)
arrayOfVariantOfBSTR63(0) = "Part"
Dim bSTR214 As String
Set selection34Variant = selection34
bSTR214 = selection34Variant.SelectElement2(arrayOfVariantOfBSTR63, "Sélectionner un élément de la visserie", False)

Dim selectedElement67 As SelectedElement
Set selectedElement67 = selection34.Item(1)

Set product28 = selectedElement67.LeafProduct

Set products1 = product28.Parent

Set product1 = products1.Parent

Dim bSTR215 As String
bSTR215 = product1.PartNumber

selection34.Clear

Set productDocument1 = CATIA.ActiveDocument

Set selection34 = productDocument1.Selection

selection34.Clear

Dim arrayOfVariantOfBSTR64(0)
arrayOfVariantOfBSTR64(0) = "Part"
Dim bSTR216 As String
Set selection34Variant = selection34
bSTR216 = selection34Variant.SelectElement2(arrayOfVariantOfBSTR64, "Sélectionner un élément de la visserie", False)

Dim selectedElement68 As SelectedElement
Set selectedElement68 = selection34.Item(1)

Set product37 = selectedElement68.LeafProduct

Set products17 = product37.Parent

Set product36 = products17.Parent

Dim bSTR217 As String
bSTR217 = product36.PartNumber

Dim selectedElement69 As SelectedElement
Set selectedElement69 = selection34.Item(1)

Set product37 = selectedElement69.LeafProduct

Set products17 = product37.Parent

Set product36 = products17.Parent

Set products17 = product36.Products

Set product37 = products17.Item(1)

Set product38 = products17.Item(2)

Dim bSTR218 As String
bSTR218 = product37.PartNumber

Dim bSTR219 As String
bSTR219 = product37.PartNumber

selection34.Clear

Set products17 = product36.Products

Set product37 = products17.Item(1)

Set product38 = products17.Item(2)

Dim bSTR220 As String
bSTR220 = product37.PartNumber

Set productDocument1 = CATIA.ActiveDocument

Set product1 = productDocument1.Product

Set products1 = product1.Products

Set productDocument1 = CATIA.ActiveDocument

Set product1 = productDocument1.Product

Set products1 = product1.Products

Set product2 = products1.Item("LaVisserie")

Set products2 = product2.Products

Dim product49 As Product
Set product49 = products2.AddNewProduct("setOutil")

Dim products26 As Products
Set products26 = product49.Products

Dim arrayOfVariantOfBSTR65(0)
arrayOfVariantOfBSTR65(0) = "D:\documents\Centrale Lyon\S8\PLM\insertion_vis\catalogue_vis_ecrou_rondelle\outils\_4.CATPart"
Set products26Variant = products26
products26Variant.AddComponentsFromFiles arrayOfVariantOfBSTR65, "All"

Set products26 = product49.Products

Set Nothing1 = products26.Item("_4.1")

Set productDocument1 = CATIA.ActiveDocument

Set product1 = productDocument1.Product

Set products1 = product1.Products

Set productDocument1 = CATIA.ActiveDocument

Dim selection35 As Selection
Set selection35 = productDocument1.Selection

selection35.Search "Name=LaVisserie*,all"

Dim long26 As Long
long26 = selection35.Count

Set productDocument1 = CATIA.ActiveDocument

Set product1 = productDocument1.Product

Set products1 = product1.Products

Set product2 = products1.Item("LaVisserie")

Dim bSTR221 As String
bSTR221 = product2.DescriptionRef

Set productDocument1 = CATIA.ActiveDocument

Set selection35 = productDocument1.Selection

selection35.Clear

Dim arrayOfVariantOfBSTR66(0)
arrayOfVariantOfBSTR66(0) = "Part"
Dim bSTR222 As String
Set selection35Variant = selection35
bSTR222 = selection35Variant.SelectElement2(arrayOfVariantOfBSTR66, "Sélectionner un élément de la visserie", False)

Dim selectedElement70 As SelectedElement
Set selectedElement70 = selection35.Item(1)

Set product37 = selectedElement70.LeafProduct

Set products17 = product37.Parent

Set product36 = products17.Parent

Dim bSTR223 As String
bSTR223 = product36.PartNumber

Dim selectedElement71 As SelectedElement
Set selectedElement71 = selection35.Item(1)

Set product37 = selectedElement71.LeafProduct

Set products17 = product37.Parent

Set product36 = products17.Parent

Set products17 = product36.Products

Set product37 = products17.Item(1)

Set product38 = products17.Item(2)

Dim bSTR224 As String
bSTR224 = product37.PartNumber

Dim bSTR225 As String
bSTR225 = product37.PartNumber

selection35.Clear

Set products17 = product36.Products

Set product37 = products17.Item(1)

Set product38 = products17.Item(2)

Dim bSTR226 As String
bSTR226 = product37.PartNumber

Set productDocument1 = CATIA.ActiveDocument

Set product1 = productDocument1.Product

Set products1 = product1.Products

Set productDocument1 = CATIA.ActiveDocument

Set product1 = productDocument1.Product

Set products1 = product1.Products

Set product2 = products1.Item("LaVisserie")

Set products2 = product2.Products

Dim product50 As Product
Set product50 = products2.AddNewProduct("setOutil")

Dim products27 As Products
Set products27 = product50.Products

Dim arrayOfVariantOfBSTR67(0)
arrayOfVariantOfBSTR67(0) = "D:\documents\Centrale Lyon\S8\PLM\insertion_vis\catalogue_vis_ecrou_rondelle\outils\_4.CATPart"
Set products27Variant = products27
products27Variant.AddComponentsFromFiles arrayOfVariantOfBSTR67, "All"

Set products27 = product50.Products

Set Nothing1 = products27.Item("_4.1")

Set productDocument1 = CATIA.ActiveDocument

Set product1 = productDocument1.Product

Set products1 = product1.Products

Set productDocument1 = CATIA.ActiveDocument

Dim selection36 As Selection
Set selection36 = productDocument1.Selection

selection36.Search "Name=LaVisserie*,all"

Dim long27 As Long
long27 = selection36.Count

Set productDocument1 = CATIA.ActiveDocument

Set product1 = productDocument1.Product

Set products1 = product1.Products

Set product2 = products1.Item("LaVisserie")

Dim bSTR227 As String
bSTR227 = product2.DescriptionRef

Set productDocument1 = CATIA.ActiveDocument

Set selection36 = productDocument1.Selection

selection36.Clear

Dim arrayOfVariantOfBSTR68(0)
arrayOfVariantOfBSTR68(0) = "Part"
Dim bSTR228 As String
Set selection36Variant = selection36
bSTR228 = selection36Variant.SelectElement2(arrayOfVariantOfBSTR68, "Sélectionner un élément de la visserie", False)

Dim selectedElement72 As SelectedElement
Set selectedElement72 = selection36.Item(1)

Set product37 = selectedElement72.LeafProduct

Set products17 = product37.Parent

Set product36 = products17.Parent

Dim bSTR229 As String
bSTR229 = product36.PartNumber

Dim selectedElement73 As SelectedElement
Set selectedElement73 = selection36.Item(1)

Set product37 = selectedElement73.LeafProduct

Set products17 = product37.Parent

Set product36 = products17.Parent

Set products17 = product36.Products

Set product37 = products17.Item(1)

Set product38 = products17.Item(2)

Dim bSTR230 As String
bSTR230 = product37.PartNumber

Dim bSTR231 As String
bSTR231 = product37.PartNumber

selection36.Clear

Set products17 = product36.Products

Set product37 = products17.Item(1)

Set product38 = products17.Item(2)

Dim bSTR232 As String
bSTR232 = product37.PartNumber

Set productDocument1 = CATIA.ActiveDocument

Set product1 = productDocument1.Product

Set products1 = product1.Products

Set productDocument1 = CATIA.ActiveDocument

Set product1 = productDocument1.Product

Set products1 = product1.Products

Set product2 = products1.Item("LaVisserie")

Set products2 = product2.Products

Dim product51 As Product
Set product51 = products2.AddNewProduct("setOutil")

Dim products28 As Products
Set products28 = product51.Products

Dim arrayOfVariantOfBSTR69(0)
arrayOfVariantOfBSTR69(0) = "D:\documents\Centrale Lyon\S8\PLM\insertion_vis\catalogue_vis_ecrou_rondelle\outils\_4.CATPart"
Set products28Variant = products28
products28Variant.AddComponentsFromFiles arrayOfVariantOfBSTR69, "All"

Set products28 = product51.Products

Set Nothing1 = products28.Item("_4.1")

Set productDocument1 = CATIA.ActiveDocument

Set product1 = productDocument1.Product

Set products1 = product1.Products

Set productDocument1 = CATIA.ActiveDocument

Dim selection37 As Selection
Set selection37 = productDocument1.Selection

selection37.Search "Name=LaVisserie*,all"

Dim long28 As Long
long28 = selection37.Count

Set productDocument1 = CATIA.ActiveDocument

Set product1 = productDocument1.Product

Set products1 = product1.Products

Set product2 = products1.Item("LaVisserie")

Dim bSTR233 As String
bSTR233 = product2.DescriptionRef

Set productDocument1 = CATIA.ActiveDocument

Set selection37 = productDocument1.Selection

selection37.Clear

Dim arrayOfVariantOfBSTR70(0)
arrayOfVariantOfBSTR70(0) = "Part"
Dim bSTR234 As String
Set selection37Variant = selection37
bSTR234 = selection37Variant.SelectElement2(arrayOfVariantOfBSTR70, "Sélectionner un élément de la visserie", False)

Dim selectedElement74 As SelectedElement
Set selectedElement74 = selection37.Item(1)

Set product37 = selectedElement74.LeafProduct

Set products17 = product37.Parent

Set product36 = products17.Parent

Dim bSTR235 As String
bSTR235 = product36.PartNumber

Dim selectedElement75 As SelectedElement
Set selectedElement75 = selection37.Item(1)

Set product37 = selectedElement75.LeafProduct

Set products17 = product37.Parent

Set product36 = products17.Parent

Set products17 = product36.Products

Set product37 = products17.Item(1)

Set product38 = products17.Item(2)

Dim bSTR236 As String
bSTR236 = product37.PartNumber

Dim bSTR237 As String
bSTR237 = product37.PartNumber

selection37.Clear

Set products17 = product36.Products

Set product37 = products17.Item(1)

Set product38 = products17.Item(2)

Dim bSTR238 As String
bSTR238 = product37.PartNumber

Set productDocument1 = CATIA.ActiveDocument

Set product1 = productDocument1.Product

Set products1 = product1.Products

Set productDocument1 = CATIA.ActiveDocument

Set product1 = productDocument1.Product

Set products1 = product1.Products

Set product2 = products1.Item("LaVisserie")

Set products2 = product2.Products

Dim product52 As Product
Set product52 = products2.AddNewProduct("setOutil")

Dim products29 As Products
Set products29 = product52.Products

Dim arrayOfVariantOfBSTR71(0)
arrayOfVariantOfBSTR71(0) = "D:\documents\Centrale Lyon\S8\PLM\insertion_vis\catalogue_vis_ecrou_rondelle\outils\_4.CATPart"
Set products29Variant = products29
products29Variant.AddComponentsFromFiles arrayOfVariantOfBSTR71, "All"

Set products29 = product52.Products

Set Nothing1 = products29.Item("_4.1")

Set productDocument1 = CATIA.ActiveDocument

Set product1 = productDocument1.Product

Set products1 = product1.Products

Set productDocument1 = CATIA.ActiveDocument

Dim selection38 As Selection
Set selection38 = productDocument1.Selection

selection38.Search "Name=LaVisserie*,all"

Dim long29 As Long
long29 = selection38.Count

Set productDocument1 = CATIA.ActiveDocument

Set product1 = productDocument1.Product

Set products1 = product1.Products

Set product2 = products1.Item("LaVisserie")

Dim bSTR239 As String
bSTR239 = product2.DescriptionRef

Set productDocument1 = CATIA.ActiveDocument

Set selection38 = productDocument1.Selection

selection38.Clear

Dim arrayOfVariantOfBSTR72(0)
arrayOfVariantOfBSTR72(0) = "Part"
Dim bSTR240 As String
Set selection38Variant = selection38
bSTR240 = selection38Variant.SelectElement2(arrayOfVariantOfBSTR72, "Sélectionner un élément de la visserie", False)

Dim selectedElement76 As SelectedElement
Set selectedElement76 = selection38.Item(1)

Set product37 = selectedElement76.LeafProduct

Set products17 = product37.Parent

Set product36 = products17.Parent

Dim bSTR241 As String
bSTR241 = product36.PartNumber

Dim selectedElement77 As SelectedElement
Set selectedElement77 = selection38.Item(1)

Set product37 = selectedElement77.LeafProduct

Set products17 = product37.Parent

Set product36 = products17.Parent

Set products17 = product36.Products

Set product37 = products17.Item(1)

Set product38 = products17.Item(2)

Dim bSTR242 As String
bSTR242 = product37.PartNumber

Dim bSTR243 As String
bSTR243 = product37.PartNumber

selection38.Clear

Set products17 = product36.Products

Set product37 = products17.Item(1)

Set product38 = products17.Item(2)

Dim bSTR244 As String
bSTR244 = product37.PartNumber

Set productDocument1 = CATIA.ActiveDocument

Set product1 = productDocument1.Product

Set products1 = product1.Products

Set productDocument1 = CATIA.ActiveDocument

Set product1 = productDocument1.Product

Set products1 = product1.Products

Set product2 = products1.Item("LaVisserie")

Set products2 = product2.Products

Dim product53 As Product
Set product53 = products2.AddNewProduct("setOutil")

Dim products30 As Products
Set products30 = product53.Products

Dim arrayOfVariantOfBSTR73(0)
arrayOfVariantOfBSTR73(0) = "D:\documents\Centrale Lyon\S8\PLM\insertion_vis\catalogue_vis_ecrou_rondelle\outils\_4.CATPart"
Set products30Variant = products30
products30Variant.AddComponentsFromFiles arrayOfVariantOfBSTR73, "All"

Set products30 = product53.Products

Set Nothing1 = products30.Item("_4.1")

Set productDocument1 = CATIA.ActiveDocument

Dim selection39 As Selection
Set selection39 = productDocument1.Selection

selection39.Clear

Dim arrayOfVariantOfBSTR74(0)
arrayOfVariantOfBSTR74(0) = "Part"
Dim bSTR245 As String
Set selection39Variant = selection39
bSTR245 = selection39Variant.SelectElement2(arrayOfVariantOfBSTR74, "Sélectionner un élément de la visserie", False)

Dim selectedElement78 As SelectedElement
Set selectedElement78 = selection39.Item(1)

Set product37 = selectedElement78.LeafProduct

Set products17 = product37.Parent

Set product36 = products17.Parent

Dim bSTR246 As String
bSTR246 = product36.PartNumber

Dim selectedElement79 As SelectedElement
Set selectedElement79 = selection39.Item(1)

Set product37 = selectedElement79.LeafProduct

Set products17 = product37.Parent

Set product36 = products17.Parent

Set products17 = product36.Products

Set product37 = products17.Item(1)

Set product38 = products17.Item(2)

Dim bSTR247 As String
bSTR247 = product37.PartNumber

Dim bSTR248 As String
bSTR248 = product37.PartNumber

selection39.Clear

Set products17 = product36.Products

Set product37 = products17.Item(1)

Set product38 = products17.Item(2)

Dim bSTR249 As String
bSTR249 = product37.PartNumber

Set productDocument1 = CATIA.ActiveDocument

Set product1 = productDocument1.Product

Set products1 = product1.Products

Set productDocument1 = CATIA.ActiveDocument

Dim selection40 As Selection
Set selection40 = productDocument1.Selection

selection40.Search "Name=LaVisserie*,all"

Dim long30 As Long
long30 = selection40.Count

Set productDocument1 = CATIA.ActiveDocument

Set product1 = productDocument1.Product

Set products1 = product1.Products

Set product2 = products1.Item("LaVisserie")

Dim bSTR250 As String
bSTR250 = product2.DescriptionRef

Set productDocument1 = CATIA.ActiveDocument

Set selection40 = productDocument1.Selection

selection40.Clear

Dim arrayOfVariantOfBSTR75(0)
arrayOfVariantOfBSTR75(0) = "Part"
Dim bSTR251 As String
Set selection40Variant = selection40
bSTR251 = selection40Variant.SelectElement2(arrayOfVariantOfBSTR75, "Sélectionner un élément de la visserie", False)

Dim selectedElement80 As SelectedElement
Set selectedElement80 = selection40.Item(1)

Set product37 = selectedElement80.LeafProduct

Set products17 = product37.Parent

Set product36 = products17.Parent

Dim bSTR252 As String
bSTR252 = product36.PartNumber

Dim selectedElement81 As SelectedElement
Set selectedElement81 = selection40.Item(1)

Set product37 = selectedElement81.LeafProduct

Set products17 = product37.Parent

Set product36 = products17.Parent

Set products17 = product36.Products

Set product37 = products17.Item(1)

Set product38 = products17.Item(2)

Dim bSTR253 As String
bSTR253 = product37.PartNumber

Dim bSTR254 As String
bSTR254 = product37.PartNumber

selection40.Clear

Set products17 = product36.Products

Set product37 = products17.Item(1)

Set product38 = products17.Item(2)

Dim bSTR255 As String
bSTR255 = product37.PartNumber

Set productDocument1 = CATIA.ActiveDocument

Set product1 = productDocument1.Product

Set products1 = product1.Products

Set productDocument1 = CATIA.ActiveDocument

Set product1 = productDocument1.Product

Set products1 = product1.Products

Set product2 = products1.Item("LaVisserie")

Set products2 = product2.Products

Dim product54 As Product
Set product54 = products2.AddNewProduct("setOutil")

Dim products31 As Products
Set products31 = product54.Products

Dim arrayOfVariantOfBSTR76(0)
arrayOfVariantOfBSTR76(0) = "D:\documents\Centrale Lyon\S8\PLM\insertion_vis\catalogue_vis_ecrou_rondelle\outils\_4.CATPart"
Set products31Variant = products31
products31Variant.AddComponentsFromFiles arrayOfVariantOfBSTR76, "All"

Set products31 = product54.Products

Set Nothing1 = products31.Item("_4.1")

Set productDocument1 = CATIA.ActiveDocument

Set product1 = productDocument1.Product

Set products1 = product1.Products

Set productDocument1 = CATIA.ActiveDocument

Dim selection41 As Selection
Set selection41 = productDocument1.Selection

selection41.Search "Name=LaVisserie*,all"

Dim long31 As Long
long31 = selection41.Count

Set productDocument1 = CATIA.ActiveDocument

Set product1 = productDocument1.Product

Set products1 = product1.Products

Set product2 = products1.Item("LaVisserie")

Dim bSTR256 As String
bSTR256 = product2.DescriptionRef

Set productDocument1 = CATIA.ActiveDocument

Set selection41 = productDocument1.Selection

selection41.Clear

Dim arrayOfVariantOfBSTR77(0)
arrayOfVariantOfBSTR77(0) = "Part"
Dim bSTR257 As String
Set selection41Variant = selection41
bSTR257 = selection41Variant.SelectElement2(arrayOfVariantOfBSTR77, "Sélectionner un élément de la visserie", False)

Dim selectedElement82 As SelectedElement
Set selectedElement82 = selection41.Item(1)

Set product37 = selectedElement82.LeafProduct

Set products17 = product37.Parent

Set product36 = products17.Parent

Dim bSTR258 As String
bSTR258 = product36.PartNumber

Dim selectedElement83 As SelectedElement
Set selectedElement83 = selection41.Item(1)

Set product37 = selectedElement83.LeafProduct

Set products17 = product37.Parent

Set product36 = products17.Parent

Set products17 = product36.Products

Set product37 = products17.Item(1)

Set product38 = products17.Item(2)

Dim bSTR259 As String
bSTR259 = product37.PartNumber

Dim bSTR260 As String
bSTR260 = product37.PartNumber

selection41.Clear

Set products17 = product36.Products

Set product37 = products17.Item(1)

Set product38 = products17.Item(2)

Dim bSTR261 As String
bSTR261 = product37.PartNumber

Set productDocument1 = CATIA.ActiveDocument

Set product1 = productDocument1.Product

Set products1 = product1.Products

Set productDocument1 = CATIA.ActiveDocument

Set product1 = productDocument1.Product

Set products1 = product1.Products

Set product2 = products1.Item("LaVisserie")

Set products2 = product2.Products

Dim product55 As Product
Set product55 = products2.AddNewProduct("setOutil")

Dim products32 As Products
Set products32 = product55.Products

Dim arrayOfVariantOfBSTR78(0)
arrayOfVariantOfBSTR78(0) = "D:\documents\Centrale Lyon\S8\PLM\insertion_vis\catalogue_vis_ecrou_rondelle\outils\_7.CATPart"
Set products32Variant = products32
products32Variant.AddComponentsFromFiles arrayOfVariantOfBSTR78, "All"

Set products32 = product55.Products

Set Nothing1 = products32.Item("_7.1")

Set productDocument1 = CATIA.ActiveDocument

Set product1 = productDocument1.Product

Set products1 = product1.Products

Set productDocument1 = CATIA.ActiveDocument

Dim selection42 As Selection
Set selection42 = productDocument1.Selection

selection42.Search "Name=LaVisserie*,all"

Dim long32 As Long
long32 = selection42.Count

Set productDocument1 = CATIA.ActiveDocument

Set product1 = productDocument1.Product

Set products1 = product1.Products

Set product2 = products1.Item("LaVisserie")

Dim bSTR262 As String
bSTR262 = product2.DescriptionRef

Set productDocument1 = CATIA.ActiveDocument

Set selection42 = productDocument1.Selection

selection42.Clear

Dim arrayOfVariantOfBSTR79(0)
arrayOfVariantOfBSTR79(0) = "Part"
Dim bSTR263 As String
Set selection42Variant = selection42
bSTR263 = selection42Variant.SelectElement2(arrayOfVariantOfBSTR79, "Sélectionner un élément de la visserie", False)

Dim selectedElement84 As SelectedElement
Set selectedElement84 = selection42.Item(1)

Set product37 = selectedElement84.LeafProduct

Set products17 = product37.Parent

Set product36 = products17.Parent

Dim bSTR264 As String
bSTR264 = product36.PartNumber

Dim selectedElement85 As SelectedElement
Set selectedElement85 = selection42.Item(1)

Set product37 = selectedElement85.LeafProduct

Set products17 = product37.Parent

Set product36 = products17.Parent

Set products17 = product36.Products

Set product37 = products17.Item(1)

Set product38 = products17.Item(2)

Dim bSTR265 As String
bSTR265 = product37.PartNumber

Dim bSTR266 As String
bSTR266 = product37.PartNumber

selection42.Clear

Set products17 = product36.Products

Set product37 = products17.Item(1)

Set product38 = products17.Item(2)

Dim bSTR267 As String
bSTR267 = product37.PartNumber

Set productDocument1 = CATIA.ActiveDocument

Set product1 = productDocument1.Product

Set products1 = product1.Products

Set productDocument1 = CATIA.ActiveDocument

Set product1 = productDocument1.Product

Set products1 = product1.Products

Set product2 = products1.Item("LaVisserie")

Set products2 = product2.Products

Dim product56 As Product
Set product56 = products2.AddNewProduct("setOutil")

Dim products33 As Products
Set products33 = product56.Products

Dim arrayOfVariantOfBSTR80(0)
arrayOfVariantOfBSTR80(0) = "D:\documents\Centrale Lyon\S8\PLM\insertion_vis\catalogue_vis_ecrou_rondelle\outils\_7.CATPart"
Set products33Variant = products33
products33Variant.AddComponentsFromFiles arrayOfVariantOfBSTR80, "All"

Set products33 = product56.Products

Set Nothing1 = products33.Item("_7.1")

Set productDocument1 = CATIA.ActiveDocument

Dim selection43 As Selection
Set selection43 = productDocument1.Selection

selection43.Clear

selection43.Add product49

selection43.Add product50

selection43.Add product51

selection43.Add product52

selection43.Add product53

selection43.Add product54

selection43.Add product55

selection43.Add product56

selection43.Delete

Set productDocument1 = CATIA.ActiveDocument

Set product1 = productDocument1.Product

Set products1 = product1.Products

Set productDocument1 = CATIA.ActiveDocument

Dim selection44 As Selection
Set selection44 = productDocument1.Selection

selection44.Search "Name=LaVisserie*,all"

Dim long33 As Long
long33 = selection44.Count

Set productDocument1 = CATIA.ActiveDocument

Set product1 = productDocument1.Product

Set products1 = product1.Products

Set product2 = products1.Item("LaVisserie")

Dim bSTR268 As String
bSTR268 = product2.DescriptionRef

Set productDocument1 = CATIA.ActiveDocument

Set selection44 = productDocument1.Selection

selection44.Clear

Dim arrayOfVariantOfBSTR81(0)
arrayOfVariantOfBSTR81(0) = "Part"
Dim bSTR269 As String
Set selection44Variant = selection44
bSTR269 = selection44Variant.SelectElement2(arrayOfVariantOfBSTR81, "Sélectionner un élément de la visserie", False)

Dim selectedElement86 As SelectedElement
Set selectedElement86 = selection44.Item(1)

Set product37 = selectedElement86.LeafProduct

Set products17 = product37.Parent

Set product36 = products17.Parent

Dim bSTR270 As String
bSTR270 = product36.PartNumber

Dim selectedElement87 As SelectedElement
Set selectedElement87 = selection44.Item(1)

Set product37 = selectedElement87.LeafProduct

Set products17 = product37.Parent

Set product36 = products17.Parent

Set products17 = product36.Products

Set product37 = products17.Item(1)

Set product38 = products17.Item(2)

Dim bSTR271 As String
bSTR271 = product37.PartNumber

Dim bSTR272 As String
bSTR272 = product37.PartNumber

selection44.Clear

Set products17 = product36.Products

Set product37 = products17.Item(1)

Set product38 = products17.Item(2)

Dim bSTR273 As String
bSTR273 = product37.PartNumber

Set productDocument1 = CATIA.ActiveDocument

Set product1 = productDocument1.Product

Set products1 = product1.Products

Set productDocument1 = CATIA.ActiveDocument

Set product1 = productDocument1.Product

Set products1 = product1.Products

Set product2 = products1.Item("LaVisserie")

Set products2 = product2.Products

Dim product57 As Product
Set product57 = products2.AddNewProduct("setOutil")

Dim products34 As Products
Set products34 = product57.Products

Dim arrayOfVariantOfBSTR82(0)
arrayOfVariantOfBSTR82(0) = "D:\documents\Centrale Lyon\S8\PLM\insertion_vis\catalogue_vis_ecrou_rondelle\outils\_7.CATPart"
Set products34Variant = products34
products34Variant.AddComponentsFromFiles arrayOfVariantOfBSTR82, "All"

Set products34 = product57.Products

Set Nothing1 = products34.Item("_7.1")

Set productDocument1 = CATIA.ActiveDocument

productDocument1.Save

Dim specsAndGeomWindow1 As SpecsAndGeomWindow
Set specsAndGeomWindow1 = CATIA.ActiveWindow

specsAndGeomWindow1.Close

Set productDocument1 = CATIA.ActiveDocument

productDocument1.Close

Set documents1 = CATIA.Documents

Dim productDocument2 As ProductDocument
Set productDocument2 = documents1.Open("D:\documents\Centrale Lyon\S8\PLM\insertion_vis\product de test.CATProduct")

Set productDocument2 = CATIA.ActiveDocument

Dim selection45 As Selection
Set selection45 = productDocument2.Selection

selection45.Clear

Dim product58 As Product
Set product58 = productDocument2.Product

Dim constraints3 As Constraints
Set constraints3 = product58.Connections("CATIAConstraints")

Dim constraint22 As Constraint
Set constraint22 = constraints3.Item("Coïncidence.54")

selection45.Add constraint22

Dim constraint23 As Constraint
Set constraint23 = constraints3.Item("Contact surfacique.57")

selection45.Add constraint23

Dim constraint24 As Constraint
Set constraint24 = constraints3.Item("Coïncidence.53")

selection45.Add constraint24

Dim constraint25 As Constraint
Set constraint25 = constraints3.Item("Contact surfacique.56")

selection45.Add constraint25

Dim constraint26 As Constraint
Set constraint26 = constraints3.Item("Contact surfacique.58")

selection45.Add constraint26

Dim constraint27 As Constraint
Set constraint27 = constraints3.Item("Coïncidence.52")

selection45.Add constraint27

Dim constraint28 As Constraint
Set constraint28 = constraints3.Item("Contact surfacique.55")

selection45.Add constraint28

Dim constraint29 As Constraint
Set constraint29 = constraints3.Item("Coïncidence.51")

selection45.Add constraint29

Dim products35 As Products
Set products35 = product58.Products

Dim product59 As Product
Set product59 = products35.Item("LaVisserie")

selection45.Add product59

selection45.Delete

Set productDocument2 = CATIA.ActiveDocument

Dim selection46 As Selection
Set selection46 = productDocument2.Selection

selection46.Clear

selection46.Add product58

selection46.Delete

Set productDocument2 = CATIA.ActiveDocument

Dim selection47 As Selection
Set selection47 = productDocument2.Selection

selection47.Delete

Set productDocument2 = CATIA.ActiveDocument

Dim selection48 As Selection
Set selection48 = productDocument2.Selection

selection48.Delete

Set productDocument2 = CATIA.ActiveDocument

Dim selection49 As Selection
Set selection49 = productDocument2.Selection

selection49.Delete

Set productDocument2 = CATIA.ActiveDocument

Dim selection50 As Selection
Set selection50 = productDocument2.Selection

selection50.Delete

Set productDocument2 = CATIA.ActiveDocument

Dim selection51 As Selection
Set selection51 = productDocument2.Selection

selection51.Delete

Set productDocument2 = CATIA.ActiveDocument

Dim selection52 As Selection
Set selection52 = productDocument2.Selection

selection52.Delete

Set productDocument2 = CATIA.ActiveDocument

Set product58 = productDocument2.Product

Set products35 = product58.Products

Set productDocument2 = CATIA.ActiveDocument

Dim selection53 As Selection
Set selection53 = productDocument2.Selection

selection53.Search "Name=LaVisserie*,all"

Dim long34 As Long
long34 = selection53.Count

Dim product60 As Product
Set product60 = products35.AddNewProduct("LaVisserie")

product60.Name = "LaVisserie"

product60.DescriptionRef = "D:\documents\Centrale Lyon\S8\PLM\insertion_vis\catalogue_vis_ecrou_rondelle\"

Dim bSTR274 As String
bSTR274 = product60.DescriptionRef

Set productDocument2 = CATIA.ActiveDocument

Set selection53 = productDocument2.Selection

selection53.Clear

Dim arrayOfVariantOfBSTR83(0)
arrayOfVariantOfBSTR83(0) = "Publication"
Dim bSTR275 As String
Set selection53Variant = selection53
bSTR275 = selection53Variant.SelectElement2(arrayOfVariantOfBSTR83, "Selectionner l'axe du trou", False)

Dim selectedElement88 As SelectedElement
Set selectedElement88 = selection53.Item(1)

Dim publication49 As Publication
Set publication49 = selectedElement88.Value

Dim selectedElement89 As SelectedElement
Set selectedElement89 = selection53.Item(1)

Set publication49 = selectedElement89.Value

Dim product61 As Product
Set product61 = products35.Item("Pièce1.1")

Dim publications23 As Publications
Set publications23 = product61.Publications

Set publication49 = publications23.Item("Axe")

Dim selectedElement90 As SelectedElement
Set selectedElement90 = selection53.Item(1)

Set publication49 = selectedElement90.Value

Set product61 = publications23.Parent

Dim bSTR276 As String
bSTR276 = product61.Name

Dim selectedElement91 As SelectedElement
Set selectedElement91 = selection53.Item(1)

Set publication49 = selectedElement91.Value

selection53.Clear

Set productDocument2 = CATIA.ActiveDocument

Set selection53 = productDocument2.Selection

selection53.Clear

Dim arrayOfVariantOfBSTR84(0)
arrayOfVariantOfBSTR84(0) = "Publication"
Dim bSTR277 As String
Set selection53Variant = selection53
bSTR277 = selection53Variant.SelectElement2(arrayOfVariantOfBSTR84, "Selectionner la face de contact de tête", False)

Dim selectedElement92 As SelectedElement
Set selectedElement92 = selection53.Item(1)

Dim publication50 As Publication
Set publication50 = selectedElement92.Value

Dim selectedElement93 As SelectedElement
Set selectedElement93 = selection53.Item(1)

Set publication50 = selectedElement93.Value

Set publication50 = publications23.Item("Face")

Dim selectedElement94 As SelectedElement
Set selectedElement94 = selection53.Item(1)

Set publication50 = selectedElement94.Value

Set product61 = publications23.Parent

Dim bSTR278 As String
bSTR278 = product61.Name

Dim selectedElement95 As SelectedElement
Set selectedElement95 = selection53.Item(1)

Set publication50 = selectedElement95.Value

selection53.Clear

Set productDocument2 = CATIA.ActiveDocument

Set selection53 = productDocument2.Selection

selection53.Clear

Dim arrayOfVariantOfBSTR85(0)
arrayOfVariantOfBSTR85(0) = "Publication"
Dim bSTR279 As String
Set selection53Variant = selection53
bSTR279 = selection53Variant.SelectElement2(arrayOfVariantOfBSTR85, "Selectionner la face de contact écrou", False)

Dim selectedElement96 As SelectedElement
Set selectedElement96 = selection53.Item(1)

Dim publication51 As Publication
Set publication51 = selectedElement96.Value

Dim selectedElement97 As SelectedElement
Set selectedElement97 = selection53.Item(1)

Set publication51 = selectedElement97.Value

Set publication51 = publications23.Item("Face1")

Dim selectedElement98 As SelectedElement
Set selectedElement98 = selection53.Item(1)

Set publication51 = selectedElement98.Value

Set product61 = publications23.Parent

Dim bSTR280 As String
bSTR280 = product61.Name

Dim selectedElement99 As SelectedElement
Set selectedElement99 = selection53.Item(1)

Set publication51 = selectedElement99.Value

Set productDocument2 = CATIA.ActiveDocument

Dim sPAWorkbench2 As SPAWorkbench
Set sPAWorkbench2 = productDocument2.GetWorkbench("SPAWorkbench")

Dim reference28 As Reference
' No resolution found for the object reference28...

Dim measurable5 As Measurable
Set measurable5 = sPAWorkbench2.GetMeasurable(reference28)

Dim reference29 As Reference
' No resolution found for the object reference29...

Dim double7 As Double
double7 = measurable5.GetMinimumDistance(reference29)

Dim reference30 As Reference
' No resolution found for the object reference30...

Dim double8 As Double
double8 = measurable5.GetMinimumDistance(reference30)

Dim measurable6 As Measurable
Set measurable6 = sPAWorkbench2.GetMeasurable(reference29)

Dim double9 As Double
double9 = measurable6.GetMinimumDistance(reference30)

selection53.Clear

Set productDocument2 = CATIA.ActiveDocument

Set product58 = productDocument2.Product

Set products35 = product58.Products

Set productDocument2 = CATIA.ActiveDocument

Set product58 = productDocument2.Product

Set products35 = product58.Products

Set product60 = products35.Item("LaVisserie")

Dim products36 As Products
Set products36 = product60.Products

Dim product62 As Product
Set product62 = products36.AddNewProduct("setVis")

Dim products37 As Products
Set products37 = product62.Products

Dim arrayOfVariantOfBSTR86(0)
arrayOfVariantOfBSTR86(0) = "D:\documents\Centrale Lyon\S8\PLM\insertion_vis\catalogue_vis_ecrou_rondelle\4x20.CATPart"
Set products37Variant = products37
products37Variant.AddComponentsFromFiles arrayOfVariantOfBSTR86, "All"

Set products37 = product62.Products

Dim product63 As Product
Set product63 = products37.Item("4x20.1")

Dim publications24 As Publications
Set publications24 = product63.Publications

Dim publication52 As Publication
Set publication52 = publications24.Item("FaceRondelle")

Set publications24 = product63.Publications

Dim publication53 As Publication
Set publication53 = publications24.Item("AxeVis")

Dim arrayOfVariantOfBSTR87(0)
arrayOfVariantOfBSTR87(0) = "D:\documents\Centrale Lyon\S8\PLM\insertion_vis\catalogue_vis_ecrou_rondelle\ecrou_M4_NS.CATPart"
Set products37Variant = products37
products37Variant.AddComponentsFromFiles arrayOfVariantOfBSTR87, "All"

Set products37 = product62.Products

Dim product64 As Product
Set product64 = products37.Item("ecrou_M4_NS.1")

Dim publications25 As Publications
Set publications25 = product64.Publications

Dim publication54 As Publication
Set publication54 = publications25.Item("FaceRondelle")

Set publications25 = product64.Publications

Dim publication55 As Publication
Set publication55 = publications25.Item("AxeVis")

Dim arrayOfVariantOfBSTR88(0)
arrayOfVariantOfBSTR88(0) = "D:\documents\Centrale Lyon\S8\PLM\insertion_vis\catalogue_vis_ecrou_rondelle\rondelle_M4.CATPart"
Set products37Variant = products37
products37Variant.AddComponentsFromFiles arrayOfVariantOfBSTR88, "All"

Set products37 = product62.Products

Dim product65 As Product
Set product65 = products37.Item("rondelle_M4.1")

Dim publications26 As Publications
Set publications26 = product65.Publications

Dim publication56 As Publication
Set publication56 = publications26.Item("FaceSup")

Set publications26 = product65.Publications

Dim publication57 As Publication
Set publication57 = publications26.Item("FaceInf")

Set publications26 = product65.Publications

Dim publication58 As Publication
Set publication58 = publications26.Item("AxeVis")

Dim arrayOfVariantOfBSTR89(0)
arrayOfVariantOfBSTR89(0) = "D:\documents\Centrale Lyon\S8\PLM\insertion_vis\catalogue_vis_ecrou_rondelle\rondelle_M4.CATPart"
Set products37Variant = products37
products37Variant.AddComponentsFromFiles arrayOfVariantOfBSTR89, "All"

Set products37 = product62.Products

Dim product66 As Product
Set product66 = products37.Item("rondelle_M4.2")

Dim publications27 As Publications
Set publications27 = product66.Publications

Dim publication59 As Publication
Set publication59 = publications27.Item("FaceSup")

Set publications27 = product66.Publications

Dim publication60 As Publication
Set publication60 = publications27.Item("FaceInf")

Set publications27 = product66.Publications

Dim publication61 As Publication
Set publication61 = publications27.Item("AxeVis")

Set productDocument2 = CATIA.ActiveDocument

Set selection53 = productDocument2.Selection

selection53.Clear

Dim bSTR281 As String
bSTR281 = product62.Name

Set products36 = product60.Products

Set product62 = products36.Item("setVis.1")

selection53.Add product62

CATIA.StartCommand "Flexible/rigide"

selection53.Clear

Set constraints3 = product58.Connections("CATIAConstraints")

Dim reference31 As Reference
' No resolution found for the object reference31...

Dim constraint30 As Constraint
Set constraint30 = constraints3.AddBiEltCst(catCstTypeOn, reference31, reference30)

Dim reference32 As Reference
' No resolution found for the object reference32...

Dim constraint31 As Constraint
Set constraint31 = constraints3.AddBiEltCst(catCstTypeOn, reference32, reference30)

Dim reference33 As Reference
' No resolution found for the object reference33...

Dim constraint32 As Constraint
Set constraint32 = constraints3.AddBiEltCst(catCstTypeOn, reference33, reference30)

Dim reference34 As Reference
' No resolution found for the object reference34...

Dim constraint33 As Constraint
Set constraint33 = constraints3.AddBiEltCst(catCstTypeOn, reference34, reference30)

Dim reference35 As Reference
' No resolution found for the object reference35...

Dim reference36 As Reference
' No resolution found for the object reference36...

Dim constraint34 As Constraint
Set constraint34 = constraints3.AddBiEltCst(catCstTypeSurfContact, reference35, reference36)

Dim reference37 As Reference
' No resolution found for the object reference37...

Dim constraint35 As Constraint
Set constraint35 = constraints3.AddBiEltCst(catCstTypeSurfContact, reference37, reference28)

Dim reference38 As Reference
' No resolution found for the object reference38...

Dim constraint36 As Constraint
Set constraint36 = constraints3.AddBiEltCst(catCstTypeSurfContact, reference29, reference38)

Dim reference39 As Reference
' No resolution found for the object reference39...

Dim reference40 As Reference
' No resolution found for the object reference40...

Dim constraint37 As Constraint
Set constraint37 = constraints3.AddBiEltCst(catCstTypeSurfContact, reference39, reference40)

Set productDocument2 = CATIA.ActiveDocument

Set selection53 = productDocument2.Selection

selection53.Clear

Dim bSTR282 As String
bSTR282 = constraint30.Name

Set constraint30 = constraints3.Item("Coïncidence.59")

selection53.Add constraint30

Dim bSTR283 As String
bSTR283 = constraint31.Name

Set constraint31 = constraints3.Item("Coïncidence.60")

selection53.Add constraint31

Dim bSTR284 As String
bSTR284 = constraint32.Name

Set constraint32 = constraints3.Item("Coïncidence.61")

selection53.Add constraint32

Dim bSTR285 As String
bSTR285 = constraint33.Name

Set constraint33 = constraints3.Item("Coïncidence.62")

selection53.Add constraint33

Dim bSTR286 As String
bSTR286 = constraint34.Name

Set constraint34 = constraints3.Item("Contact surfacique.63")

selection53.Add constraint34

Dim bSTR287 As String
bSTR287 = constraint35.Name

Set constraint35 = constraints3.Item("Contact surfacique.64")

selection53.Add constraint35

Dim bSTR288 As String
bSTR288 = constraint36.Name

Set constraint36 = constraints3.Item("Contact surfacique.65")

selection53.Add constraint36

Dim bSTR289 As String
bSTR289 = constraint37.Name

Set constraint37 = constraints3.Item("Contact surfacique.66")

selection53.Add constraint37

CATIA.StartCommand "Regrouper dans un nouveau groupe"

selection53.Clear

Set productDocument2 = CATIA.ActiveDocument

Set product58 = productDocument2.Product

product58.Update

Set productDocument2 = CATIA.ActiveDocument

Set selection53 = productDocument2.Selection

selection53.Clear

Dim arrayOfVariantOfBSTR90(0)
arrayOfVariantOfBSTR90(0) = "Part"
Dim bSTR290 As String
Set selection53Variant = selection53
bSTR290 = selection53Variant.SelectElement2(arrayOfVariantOfBSTR90, "Sélectionner un élément de la visserie", False)

Dim selectedElement100 As SelectedElement
Set selectedElement100 = selection53.Item(1)

Set product63 = selectedElement100.LeafProduct

Set products37 = product63.Parent

Set product62 = products37.Parent

Dim bSTR291 As String
bSTR291 = product62.PartNumber

Dim selectedElement101 As SelectedElement
Set selectedElement101 = selection53.Item(1)

Set product63 = selectedElement101.LeafProduct

Set products37 = product63.Parent

Set product62 = products37.Parent

Set products37 = product62.Products

Set product63 = products37.Item(1)

Set product64 = products37.Item(2)

Dim bSTR292 As String
bSTR292 = product63.PartNumber

Dim bSTR293 As String
bSTR293 = product63.PartNumber

selection53.Clear

Set products37 = product62.Products

Set product63 = products37.Item(1)

Set product64 = products37.Item(2)

Dim bSTR294 As String
bSTR294 = product63.PartNumber

Set productDocument2 = CATIA.ActiveDocument

Set product58 = productDocument2.Product

Set products35 = product58.Products

Set productDocument2 = CATIA.ActiveDocument

Set product58 = productDocument2.Product

Set products35 = product58.Products

Set product60 = products35.Item("LaVisserie")

Set products36 = product60.Products

Dim product67 As Product
Set product67 = products36.AddNewProduct("setOutil")

Dim products38 As Products
Set products38 = product67.Products

Dim arrayOfVariantOfBSTR91(0)
arrayOfVariantOfBSTR91(0) = "D:\documents\Centrale Lyon\S8\PLM\insertion_vis\catalogue_vis_ecrou_rondelle\outils\_7.CATPart"
Set products38Variant = products38
products38Variant.AddComponentsFromFiles arrayOfVariantOfBSTR91, "All"

Set products38 = product67.Products

Set Nothing1 = products38.Item("_7.1")

Set productDocument2 = CATIA.ActiveDocument

Set product58 = productDocument2.Product

Set products35 = product58.Products

Set productDocument2 = CATIA.ActiveDocument

Dim selection54 As Selection
Set selection54 = productDocument2.Selection

selection54.Search "Name=LaVisserie*,all"

Dim long35 As Long
long35 = selection54.Count

Set productDocument2 = CATIA.ActiveDocument

Set product58 = productDocument2.Product

Set products35 = product58.Products

Set product60 = products35.Item("LaVisserie")

Dim bSTR295 As String
bSTR295 = product60.DescriptionRef

Set productDocument2 = CATIA.ActiveDocument

Set selection54 = productDocument2.Selection

selection54.Clear

Dim arrayOfVariantOfBSTR92(0)
arrayOfVariantOfBSTR92(0) = "Part"
Dim bSTR296 As String
Set selection54Variant = selection54
bSTR296 = selection54Variant.SelectElement2(arrayOfVariantOfBSTR92, "Sélectionner un élément de la visserie", False)

Dim selectedElement102 As SelectedElement
Set selectedElement102 = selection54.Item(1)

Set product63 = selectedElement102.LeafProduct

Set products37 = product63.Parent

Set product62 = products37.Parent

Dim bSTR297 As String
bSTR297 = product62.PartNumber

Dim selectedElement103 As SelectedElement
Set selectedElement103 = selection54.Item(1)

Set product63 = selectedElement103.LeafProduct

Set products37 = product63.Parent

Set product62 = products37.Parent

Set products37 = product62.Products

Set product63 = products37.Item(1)

Set product64 = products37.Item(2)

Dim bSTR298 As String
bSTR298 = product63.PartNumber

Dim bSTR299 As String
bSTR299 = product63.PartNumber

selection54.Clear

Set products37 = product62.Products

Set product63 = products37.Item(1)

Set product64 = products37.Item(2)

Dim bSTR300 As String
bSTR300 = product63.PartNumber

Set productDocument2 = CATIA.ActiveDocument

Set product58 = productDocument2.Product

Set products35 = product58.Products

Set productDocument2 = CATIA.ActiveDocument

Set product58 = productDocument2.Product

Set products35 = product58.Products

Set product60 = products35.Item("LaVisserie")

Set products36 = product60.Products

Dim product68 As Product
Set product68 = products36.AddNewProduct("setOutil")

Dim products39 As Products
Set products39 = product68.Products

Dim arrayOfVariantOfBSTR93(0)
arrayOfVariantOfBSTR93(0) = "D:\documents\Centrale Lyon\S8\PLM\insertion_vis\catalogue_vis_ecrou_rondelle\outils\_7.CATPart"
Set products39Variant = products39
products39Variant.AddComponentsFromFiles arrayOfVariantOfBSTR93, "All"

Set products39 = product68.Products

Set Nothing1 = products39.Item("_7.1")

Set productDocument2 = CATIA.ActiveDocument

Set product58 = productDocument2.Product

Set products35 = product58.Products

Set productDocument2 = CATIA.ActiveDocument

Dim selection55 As Selection
Set selection55 = productDocument2.Selection

selection55.Search "Name=LaVisserie*,all"

Dim long36 As Long
long36 = selection55.Count

Set productDocument2 = CATIA.ActiveDocument

Set product58 = productDocument2.Product

Set products35 = product58.Products

Set product60 = products35.Item("LaVisserie")

Dim bSTR301 As String
bSTR301 = product60.DescriptionRef

Set productDocument2 = CATIA.ActiveDocument

Set selection55 = productDocument2.Selection

selection55.Clear

Dim arrayOfVariantOfBSTR94(0)
arrayOfVariantOfBSTR94(0) = "Part"
Dim bSTR302 As String
Set selection55Variant = selection55
bSTR302 = selection55Variant.SelectElement2(arrayOfVariantOfBSTR94, "Sélectionner un élément de la visserie", False)

Dim selectedElement104 As SelectedElement
Set selectedElement104 = selection55.Item(1)

Set product63 = selectedElement104.LeafProduct

Set products37 = product63.Parent

Set product62 = products37.Parent

Dim bSTR303 As String
bSTR303 = product62.PartNumber

Dim selectedElement105 As SelectedElement
Set selectedElement105 = selection55.Item(1)

Set product63 = selectedElement105.LeafProduct

Set products37 = product63.Parent

Set product62 = products37.Parent

Set products37 = product62.Products

Set product63 = products37.Item(1)

Set product64 = products37.Item(2)

Dim bSTR304 As String
bSTR304 = product63.PartNumber

Dim bSTR305 As String
bSTR305 = product63.PartNumber

selection55.Clear

Set products37 = product62.Products

Set product63 = products37.Item(1)

Set product64 = products37.Item(2)

Dim bSTR306 As String
bSTR306 = product63.PartNumber

Set productDocument2 = CATIA.ActiveDocument

Set product58 = productDocument2.Product

Set products35 = product58.Products

Set productDocument2 = CATIA.ActiveDocument

Set product58 = productDocument2.Product

Set products35 = product58.Products

Set product60 = products35.Item("LaVisserie")

Set products36 = product60.Products

Dim product69 As Product
Set product69 = products36.AddNewProduct("setOutil")

Dim products40 As Products
Set products40 = product69.Products

Dim arrayOfVariantOfBSTR95(0)
arrayOfVariantOfBSTR95(0) = "D:\documents\Centrale Lyon\S8\PLM\insertion_vis\catalogue_vis_ecrou_rondelle\outils\douille_7.CATPart"
Set products40Variant = products40
products40Variant.AddComponentsFromFiles arrayOfVariantOfBSTR95, "All"

Set products40 = product69.Products

Dim product70 As Product
Set product70 = products40.Item("douille_7.1")

Dim publications28 As Publications
Set publications28 = product70.Publications

Dim publication62 As Publication
Set publication62 = publications28.Item("Axe")

Set publications28 = product70.Publications

Dim publication63 As Publication
Set publication63 = publications28.Item("Face_inf")

Dim arrayOfVariantOfBSTR96(0)
arrayOfVariantOfBSTR96(0) = "D:\documents\Centrale Lyon\S8\PLM\insertion_vis\catalogue_vis_ecrou_rondelle\outils\douille_7.CATPart"
Set products40Variant = products40
products40Variant.AddComponentsFromFiles arrayOfVariantOfBSTR96, "All"

Set products40 = product69.Products

Set product70 = products40.Item("douille_7.1")

Set publications28 = product70.Publications

Set publication62 = publications28.Item("Axe")

Set publications28 = product70.Publications

Set publication63 = publications28.Item("Face_inf")

Set publications24 = product63.Publications

Set publication53 = publications24.Item("AxeVis")

Set publications24 = product63.Publications

Set publication52 = publications24.Item("FaceRondelle")

Set publications25 = product64.Publications

Set publication54 = publications25.Item("FaceRondelle")

Set productDocument2 = CATIA.ActiveDocument

Set selection55 = productDocument2.Selection

selection55.Clear

Dim bSTR307 As String
bSTR307 = product69.Name

Set products36 = product60.Products

Set product69 = products36.Item("setOutil2.1")

selection55.Add product69

CATIA.StartCommand "Flexible/rigide"

selection55.Clear

Set constraints3 = product58.Connections("CATIAConstraints")

Dim reference41 As Reference
' No resolution found for the object reference41...

Dim constraint38 As Constraint
Set constraint38 = constraints3.AddBiEltCst(catCstTypeOn, reference41, reference31)

Set productDocument2 = CATIA.ActiveDocument

Set product58 = productDocument2.Product

product58.Update

Set productDocument2 = CATIA.ActiveDocument

Dim selection56 As Selection
Set selection56 = productDocument2.Selection

selection56.Clear

selection56.Add constraint38

selection56.Add product69

selection56.Delete

Set productDocument2 = CATIA.ActiveDocument

Dim selection57 As Selection
Set selection57 = productDocument2.Selection

selection57.Clear

selection57.Add product68

selection57.Delete

Set productDocument2 = CATIA.ActiveDocument

Dim selection58 As Selection
Set selection58 = productDocument2.Selection

selection58.Clear

selection58.Add product67

selection58.Delete

Set productDocument2 = CATIA.ActiveDocument

Set product58 = productDocument2.Product

Set products35 = product58.Products

Set productDocument2 = CATIA.ActiveDocument

Dim selection59 As Selection
Set selection59 = productDocument2.Selection

selection59.Search "Name=LaVisserie*,all"

Dim long37 As Long
long37 = selection59.Count

Set productDocument2 = CATIA.ActiveDocument

Set product58 = productDocument2.Product

Set products35 = product58.Products

Set product60 = products35.Item("LaVisserie")

Dim bSTR308 As String
bSTR308 = product60.DescriptionRef

Set productDocument2 = CATIA.ActiveDocument

Set selection59 = productDocument2.Selection

selection59.Clear

Dim arrayOfVariantOfBSTR97(0)
arrayOfVariantOfBSTR97(0) = "Part"
Dim bSTR309 As String
Set selection59Variant = selection59
bSTR309 = selection59Variant.SelectElement2(arrayOfVariantOfBSTR97, "Sélectionner un élément de la visserie", False)

Dim selectedElement106 As SelectedElement
Set selectedElement106 = selection59.Item(1)

Set product63 = selectedElement106.LeafProduct

Set products37 = product63.Parent

Set product62 = products37.Parent

Dim bSTR310 As String
bSTR310 = product62.PartNumber

Dim selectedElement107 As SelectedElement
Set selectedElement107 = selection59.Item(1)

Set product63 = selectedElement107.LeafProduct

Set products37 = product63.Parent

Set product62 = products37.Parent

Set products37 = product62.Products

Set product63 = products37.Item(1)

Set product64 = products37.Item(2)

Dim bSTR311 As String
bSTR311 = product63.PartNumber

Dim bSTR312 As String
bSTR312 = product63.PartNumber

selection59.Clear

Set products37 = product62.Products

Set product63 = products37.Item(1)

Set product64 = products37.Item(2)

Dim bSTR313 As String
bSTR313 = product63.PartNumber

Set productDocument2 = CATIA.ActiveDocument

Set product58 = productDocument2.Product

Set products35 = product58.Products

Set productDocument2 = CATIA.ActiveDocument

Set product58 = productDocument2.Product

Set products35 = product58.Products

Set product60 = products35.Item("LaVisserie")

Set products36 = product60.Products

Dim product71 As Product
Set product71 = products36.AddNewProduct("setOutil")

Dim products41 As Products
Set products41 = product71.Products

Dim arrayOfVariantOfBSTR98(0)
arrayOfVariantOfBSTR98(0) = "D:\documents\Centrale Lyon\S8\PLM\insertion_vis\catalogue_vis_ecrou_rondelle\outils\douille_7.CATPart"
Set products41Variant = products41
products41Variant.AddComponentsFromFiles arrayOfVariantOfBSTR98, "All"

Set products41 = product71.Products

Dim product72 As Product
Set product72 = products41.Item("douille_7.1")

Dim publications29 As Publications
Set publications29 = product72.Publications

Dim publication64 As Publication
Set publication64 = publications29.Item("Axe")

Set publications29 = product72.Publications

Dim publication65 As Publication
Set publication65 = publications29.Item("Face_inf")

Dim arrayOfVariantOfBSTR99(0)
arrayOfVariantOfBSTR99(0) = "D:\documents\Centrale Lyon\S8\PLM\insertion_vis\catalogue_vis_ecrou_rondelle\outils\douille_7.CATPart"
Set products41Variant = products41
products41Variant.AddComponentsFromFiles arrayOfVariantOfBSTR99, "All"

Set products41 = product71.Products

Set product72 = products41.Item("douille_7.1")

Set publications29 = product72.Publications

Set publication64 = publications29.Item("Axe")

Set publications29 = product72.Publications

Set publication65 = publications29.Item("Face_inf")

Set publications24 = product63.Publications

Set publication53 = publications24.Item("AxeVis")

Set publications24 = product63.Publications

Set publication52 = publications24.Item("FaceRondelle")

Set publications25 = product64.Publications

Set publication54 = publications25.Item("FaceRondelle")

Set productDocument2 = CATIA.ActiveDocument

Set selection59 = productDocument2.Selection

selection59.Clear

Dim bSTR314 As String
bSTR314 = product71.Name

Set products36 = product60.Products

Set product71 = products36.Item("setOutil.2")

selection59.Add product71

CATIA.StartCommand "Flexible/rigide"

selection59.Clear

Set constraints3 = product58.Connections("CATIAConstraints")

Dim reference42 As Reference
' No resolution found for the object reference42...

Dim constraint39 As Constraint
Set constraint39 = constraints3.AddBiEltCst(catCstTypeOn, reference42, reference31)

Dim constraint40 As Constraint
Set constraint40 = constraints3.AddBiEltCst(catCstTypeOn, reference42, reference31)

Set productDocument2 = CATIA.ActiveDocument

Set product58 = productDocument2.Product

product58.Update

Set productDocument2 = CATIA.ActiveDocument

Dim selection60 As Selection
Set selection60 = productDocument2.Selection

selection60.Clear

selection60.Add constraint39

selection60.Delete

Set productDocument2 = CATIA.ActiveDocument

Dim selection61 As Selection
Set selection61 = productDocument2.Selection

selection61.Clear

selection61.Add constraint40

selection61.Delete

Set productDocument2 = CATIA.ActiveDocument

Dim selection62 As Selection
Set selection62 = productDocument2.Selection

selection62.Clear

selection62.Add product71

selection62.Delete

Set productDocument2 = CATIA.ActiveDocument

Set product58 = productDocument2.Product

Set products35 = product58.Products

Set productDocument2 = CATIA.ActiveDocument

Dim selection63 As Selection
Set selection63 = productDocument2.Selection

selection63.Search "Name=LaVisserie*,all"

Dim long38 As Long
long38 = selection63.Count

Set productDocument2 = CATIA.ActiveDocument

Set product58 = productDocument2.Product

Set products35 = product58.Products

Set product60 = products35.Item("LaVisserie")

Dim bSTR315 As String
bSTR315 = product60.DescriptionRef

Set productDocument2 = CATIA.ActiveDocument

Set selection63 = productDocument2.Selection

selection63.Clear

Dim arrayOfVariantOfBSTR100(0)
arrayOfVariantOfBSTR100(0) = "Part"
Dim bSTR316 As String
Set selection63Variant = selection63
bSTR316 = selection63Variant.SelectElement2(arrayOfVariantOfBSTR100, "Sélectionner un élément de la visserie", False)

Dim selectedElement108 As SelectedElement
Set selectedElement108 = selection63.Item(1)

Set product63 = selectedElement108.LeafProduct

Set products37 = product63.Parent

Set product62 = products37.Parent

Dim bSTR317 As String
bSTR317 = product62.PartNumber

Dim selectedElement109 As SelectedElement
Set selectedElement109 = selection63.Item(1)

Set product63 = selectedElement109.LeafProduct

Set products37 = product63.Parent

Set product62 = products37.Parent

Set products37 = product62.Products

Set product63 = products37.Item(1)

Set product64 = products37.Item(2)

Dim bSTR318 As String
bSTR318 = product63.PartNumber

Dim bSTR319 As String
bSTR319 = product63.PartNumber

selection63.Clear

Set products37 = product62.Products

Set product63 = products37.Item(1)

Set product64 = products37.Item(2)

Dim bSTR320 As String
bSTR320 = product63.PartNumber

Set productDocument2 = CATIA.ActiveDocument

Set product58 = productDocument2.Product

Set products35 = product58.Products

Set productDocument2 = CATIA.ActiveDocument

Set product58 = productDocument2.Product

Set products35 = product58.Products

Set product60 = products35.Item("LaVisserie")

Set products36 = product60.Products

Dim product73 As Product
Set product73 = products36.AddNewProduct("setOutil")

Dim products42 As Products
Set products42 = product73.Products

Dim arrayOfVariantOfBSTR101(0)
arrayOfVariantOfBSTR101(0) = "D:\documents\Centrale Lyon\S8\PLM\insertion_vis\catalogue_vis_ecrou_rondelle\outils\douille_7.CATPart"
Set products42Variant = products42
products42Variant.AddComponentsFromFiles arrayOfVariantOfBSTR101, "All"

Set products42 = product73.Products

Dim product74 As Product
Set product74 = products42.Item("douille_7.1")

Dim publications30 As Publications
Set publications30 = product74.Publications

Dim publication66 As Publication
Set publication66 = publications30.Item("Axe")

Set publications30 = product74.Publications

Dim publication67 As Publication
Set publication67 = publications30.Item("Face_inf")

Dim arrayOfVariantOfBSTR102(0)
arrayOfVariantOfBSTR102(0) = "D:\documents\Centrale Lyon\S8\PLM\insertion_vis\catalogue_vis_ecrou_rondelle\outils\douille_7.CATPart"
Set products42Variant = products42
products42Variant.AddComponentsFromFiles arrayOfVariantOfBSTR102, "All"

Set products42 = product73.Products

Set product74 = products42.Item("douille_7.1")

Set publications30 = product74.Publications

Set publication66 = publications30.Item("Axe")

Set publications30 = product74.Publications

Set publication67 = publications30.Item("Face_inf")

Set publications24 = product63.Publications

Set publication53 = publications24.Item("AxeVis")

Set publications24 = product63.Publications

Set publication52 = publications24.Item("FaceRondelle")

Set publications25 = product64.Publications

Set publication54 = publications25.Item("FaceRondelle")

Set productDocument2 = CATIA.ActiveDocument

Set selection63 = productDocument2.Selection

selection63.Clear

Dim bSTR321 As String
bSTR321 = product73.Name

Set products36 = product60.Products

Set product73 = products36.Item("setOutil.3")

selection63.Add product73

CATIA.StartCommand "Flexible/rigide"

selection63.Clear

Set constraints3 = product58.Connections("CATIAConstraints")

Dim reference43 As Reference
' No resolution found for the object reference43...

Dim constraint41 As Constraint
Set constraint41 = constraints3.AddBiEltCst(catCstTypeOn, reference43, reference31)

Dim constraint42 As Constraint
Set constraint42 = constraints3.AddBiEltCst(catCstTypeOn, reference43, reference31)

Set productDocument2 = CATIA.ActiveDocument

Set product58 = productDocument2.Product

product58.Update

Set products37 = product62.Products

Set product63 = products37.Item(1)

Set product64 = products37.Item(2)

Dim bSTR322 As String
bSTR322 = product63.PartNumber

Set productDocument2 = CATIA.ActiveDocument

Set product58 = productDocument2.Product

Set products35 = product58.Products

Set productDocument2 = CATIA.ActiveDocument

Set product58 = productDocument2.Product

Set products35 = product58.Products

Set product60 = products35.Item("LaVisserie")

Set products36 = product60.Products

Dim product75 As Product
Set product75 = products36.AddNewProduct("setOutil")

Dim products43 As Products
Set products43 = product75.Products

Dim arrayOfVariantOfBSTR103(0)
arrayOfVariantOfBSTR103(0) = "D:\documents\Centrale Lyon\S8\PLM\insertion_vis\catalogue_vis_ecrou_rondelle\outils\douille_7.CATPart"
Set products43Variant = products43
products43Variant.AddComponentsFromFiles arrayOfVariantOfBSTR103, "All"

Set products43 = product75.Products

Dim product76 As Product
Set product76 = products43.Item("douille_7.1")

Dim publications31 As Publications
Set publications31 = product76.Publications

Dim publication68 As Publication
Set publication68 = publications31.Item("Axe")

Set publications31 = product76.Publications

Dim publication69 As Publication
Set publication69 = publications31.Item("Face_inf")

Dim arrayOfVariantOfBSTR104(0)
arrayOfVariantOfBSTR104(0) = "D:\documents\Centrale Lyon\S8\PLM\insertion_vis\catalogue_vis_ecrou_rondelle\outils\douille_7.CATPart"
Set products43Variant = products43
products43Variant.AddComponentsFromFiles arrayOfVariantOfBSTR104, "All"

Set products43 = product75.Products

Set product76 = products43.Item("douille_7.1")

Set publications31 = product76.Publications

Set publication68 = publications31.Item("Axe")

Set publications31 = product76.Publications

Set publication69 = publications31.Item("Face_inf")

Set publications24 = product63.Publications

Set publication53 = publications24.Item("AxeVis")

Set publications24 = product63.Publications

Set publication52 = publications24.Item("FaceRondelle")

Set publications25 = product64.Publications

Set publication54 = publications25.Item("FaceRondelle")

Set productDocument2 = CATIA.ActiveDocument

Set selection63 = productDocument2.Selection

selection63.Clear

Dim bSTR323 As String
bSTR323 = product75.Name

Set products36 = product60.Products

Set product75 = products36.Item("setOutil1.2")

selection63.Add product75

CATIA.StartCommand "Flexible/rigide"

selection63.Clear

Set constraints3 = product58.Connections("CATIAConstraints")

Dim reference44 As Reference
' No resolution found for the object reference44...

Dim constraint43 As Constraint
Set constraint43 = constraints3.AddBiEltCst(catCstTypeOn, reference44, reference31)

Dim constraint44 As Constraint
Set constraint44 = constraints3.AddBiEltCst(catCstTypeOn, reference44, reference31)

Set productDocument2 = CATIA.ActiveDocument

Set product58 = productDocument2.Product

product58.Update

Set productDocument2 = CATIA.ActiveDocument

Dim selection64 As Selection
Set selection64 = productDocument2.Selection

selection64.Clear

selection64.Add constraint44

selection64.Delete

Set productDocument2 = CATIA.ActiveDocument

Dim selection65 As Selection
Set selection65 = productDocument2.Selection

selection65.Clear

selection65.Add constraint43

selection65.Delete

Set productDocument2 = CATIA.ActiveDocument

Dim selection66 As Selection
Set selection66 = productDocument2.Selection

selection66.Clear

selection66.Add product75

selection66.Delete

Set productDocument2 = CATIA.ActiveDocument

Dim selection67 As Selection
Set selection67 = productDocument2.Selection

selection67.Clear

selection67.Add constraint42

selection67.Add constraint41

selection67.Add product73

selection67.Delete

Set productDocument2 = CATIA.ActiveDocument

Set product58 = productDocument2.Product

Set products35 = product58.Products

Set productDocument2 = CATIA.ActiveDocument

Dim selection68 As Selection
Set selection68 = productDocument2.Selection

selection68.Search "Name=LaVisserie*,all"

Dim long39 As Long
long39 = selection68.Count

Set productDocument2 = CATIA.ActiveDocument

Set product58 = productDocument2.Product

Set products35 = product58.Products

Set product60 = products35.Item("LaVisserie")

Dim bSTR324 As String
bSTR324 = product60.DescriptionRef

Set productDocument2 = CATIA.ActiveDocument

Set selection68 = productDocument2.Selection

selection68.Clear

Dim arrayOfVariantOfBSTR105(0)
arrayOfVariantOfBSTR105(0) = "Part"
Dim bSTR325 As String
Set selection68Variant = selection68
bSTR325 = selection68Variant.SelectElement2(arrayOfVariantOfBSTR105, "Sélectionner un élément de la visserie", False)

Dim selectedElement110 As SelectedElement
Set selectedElement110 = selection68.Item(1)

Set product63 = selectedElement110.LeafProduct

Set products37 = product63.Parent

Set product62 = products37.Parent

Dim bSTR326 As String
bSTR326 = product62.PartNumber

Dim selectedElement111 As SelectedElement
Set selectedElement111 = selection68.Item(1)

Set product63 = selectedElement111.LeafProduct

Set products37 = product63.Parent

Set product62 = products37.Parent

Set products37 = product62.Products

Set product63 = products37.Item(1)

Set product64 = products37.Item(2)

Dim bSTR327 As String
bSTR327 = product63.PartNumber

Dim bSTR328 As String
bSTR328 = product63.PartNumber

selection68.Clear

Set products37 = product62.Products

Set product63 = products37.Item(1)

Set product64 = products37.Item(2)

Dim bSTR329 As String
bSTR329 = product63.PartNumber

Set productDocument2 = CATIA.ActiveDocument

Set product58 = productDocument2.Product

Set products35 = product58.Products

Set productDocument2 = CATIA.ActiveDocument

Set product58 = productDocument2.Product

Set products35 = product58.Products

Set product60 = products35.Item("LaVisserie")

Set products36 = product60.Products

Dim product77 As Product
Set product77 = products36.AddNewProduct("setOutil")

Dim products44 As Products
Set products44 = product77.Products

Dim arrayOfVariantOfBSTR106(0)
arrayOfVariantOfBSTR106(0) = "D:\documents\Centrale Lyon\S8\PLM\insertion_vis\catalogue_vis_ecrou_rondelle\outils\douille_7.CATPart"
Set products44Variant = products44
products44Variant.AddComponentsFromFiles arrayOfVariantOfBSTR106, "All"

Set products44 = product77.Products

Dim product78 As Product
Set product78 = products44.Item("douille_7.1")

Dim publications32 As Publications
Set publications32 = product78.Publications

Dim publication70 As Publication
Set publication70 = publications32.Item("Axe")

Set publications32 = product78.Publications

Dim publication71 As Publication
Set publication71 = publications32.Item("Face_inf")

Dim arrayOfVariantOfBSTR107(0)
arrayOfVariantOfBSTR107(0) = "D:\documents\Centrale Lyon\S8\PLM\insertion_vis\catalogue_vis_ecrou_rondelle\outils\plate_7.CATPart"
Set products44Variant = products44
products44Variant.AddComponentsFromFiles arrayOfVariantOfBSTR107, "All"

Set products44 = product77.Products

Set Nothing1 = products44.Item("plate_7.1")

Set productDocument2 = CATIA.ActiveDocument

Dim selection69 As Selection
Set selection69 = productDocument2.Selection

selection69.Clear

selection69.Add product77

selection69.Delete

Set productDocument2 = CATIA.ActiveDocument

Set product58 = productDocument2.Product

Set products35 = product58.Products

Set productDocument2 = CATIA.ActiveDocument

Dim selection70 As Selection
Set selection70 = productDocument2.Selection

selection70.Search "Name=LaVisserie*,all"

Dim long40 As Long
long40 = selection70.Count

Set productDocument2 = CATIA.ActiveDocument

Set product58 = productDocument2.Product

Set products35 = product58.Products

Set product60 = products35.Item("LaVisserie")

Dim bSTR330 As String
bSTR330 = product60.DescriptionRef

Set productDocument2 = CATIA.ActiveDocument

Set selection70 = productDocument2.Selection

selection70.Clear

Dim arrayOfVariantOfBSTR108(0)
arrayOfVariantOfBSTR108(0) = "Part"
Dim bSTR331 As String
Set selection70Variant = selection70
bSTR331 = selection70Variant.SelectElement2(arrayOfVariantOfBSTR108, "Sélectionner un élément de la visserie", False)

Dim selectedElement112 As SelectedElement
Set selectedElement112 = selection70.Item(1)

Set product63 = selectedElement112.LeafProduct

Set products37 = product63.Parent

Set product62 = products37.Parent

Dim bSTR332 As String
bSTR332 = product62.PartNumber

Dim selectedElement113 As SelectedElement
Set selectedElement113 = selection70.Item(1)

Set product63 = selectedElement113.LeafProduct

Set products37 = product63.Parent

Set product62 = products37.Parent

Set products37 = product62.Products

Set product63 = products37.Item(1)

Set product64 = products37.Item(2)

Dim bSTR333 As String
bSTR333 = product63.PartNumber

Dim bSTR334 As String
bSTR334 = product63.PartNumber

selection70.Clear

Set products37 = product62.Products

Set product63 = products37.Item(1)

Set product64 = products37.Item(2)

Dim bSTR335 As String
bSTR335 = product63.PartNumber

Set productDocument2 = CATIA.ActiveDocument

Set product58 = productDocument2.Product

Set products35 = product58.Products

Set productDocument2 = CATIA.ActiveDocument

Set product58 = productDocument2.Product

Set products35 = product58.Products

Set product60 = products35.Item("LaVisserie")

Set products36 = product60.Products

Dim product79 As Product
Set product79 = products36.AddNewProduct("setOutil")

Dim products45 As Products
Set products45 = product79.Products

Dim arrayOfVariantOfBSTR109(0)
arrayOfVariantOfBSTR109(0) = "D:\documents\Centrale Lyon\S8\PLM\insertion_vis\catalogue_vis_ecrou_rondelle\outils\plate_7.CATPart"
Set products45Variant = products45
products45Variant.AddComponentsFromFiles arrayOfVariantOfBSTR109, "All"

Set products45 = product79.Products

Set Nothing1 = products45.Item("plate_7.1")

Set productDocument2 = CATIA.ActiveDocument

Set product58 = productDocument2.Product

Set products35 = product58.Products

Set productDocument2 = CATIA.ActiveDocument

Dim selection71 As Selection
Set selection71 = productDocument2.Selection

selection71.Search "Name=LaVisserie*,all"

Dim long41 As Long
long41 = selection71.Count

Set productDocument2 = CATIA.ActiveDocument

Set product58 = productDocument2.Product

Set products35 = product58.Products

Set product60 = products35.Item("LaVisserie")

Dim bSTR336 As String
bSTR336 = product60.DescriptionRef

Set productDocument2 = CATIA.ActiveDocument

Set selection71 = productDocument2.Selection

selection71.Clear

Dim arrayOfVariantOfBSTR110(0)
arrayOfVariantOfBSTR110(0) = "Part"
Dim bSTR337 As String
Set selection71Variant = selection71
bSTR337 = selection71Variant.SelectElement2(arrayOfVariantOfBSTR110, "Sélectionner un élément de la visserie", False)

Dim selectedElement114 As SelectedElement
Set selectedElement114 = selection71.Item(1)

Set product63 = selectedElement114.LeafProduct

Set products37 = product63.Parent

Set product62 = products37.Parent

Dim bSTR338 As String
bSTR338 = product62.PartNumber

Dim selectedElement115 As SelectedElement
Set selectedElement115 = selection71.Item(1)

Set product63 = selectedElement115.LeafProduct

Set products37 = product63.Parent

Set product62 = products37.Parent

Set products37 = product62.Products

Set product63 = products37.Item(1)

Set product64 = products37.Item(2)

Dim bSTR339 As String
bSTR339 = product63.PartNumber

Dim bSTR340 As String
bSTR340 = product63.PartNumber

selection71.Clear

Set products37 = product62.Products

Set product63 = products37.Item(1)

Set product64 = products37.Item(2)

Dim bSTR341 As String
bSTR341 = product63.PartNumber

Set productDocument2 = CATIA.ActiveDocument

Set product58 = productDocument2.Product

Set products35 = product58.Products

Set productDocument2 = CATIA.ActiveDocument

Set product58 = productDocument2.Product

Set products35 = product58.Products

Set product60 = products35.Item("LaVisserie")

Set products36 = product60.Products

Dim product80 As Product
Set product80 = products36.AddNewProduct("setOutil")

Dim products46 As Products
Set products46 = product80.Products

Dim arrayOfVariantOfBSTR111(0)
arrayOfVariantOfBSTR111(0) = "D:\documents\Centrale Lyon\S8\PLM\insertion_vis\catalogue_vis_ecrou_rondelle\outils\plate_7.CATPart"
Set products46Variant = products46
products46Variant.AddComponentsFromFiles arrayOfVariantOfBSTR111, "All"

Set products46 = product80.Products

Set Nothing1 = products46.Item("plate_7.1")

Set productDocument2 = CATIA.ActiveDocument

Dim selection72 As Selection
Set selection72 = productDocument2.Selection

selection72.Clear

selection72.Add product79

selection72.Delete

Set productDocument2 = CATIA.ActiveDocument

Dim selection73 As Selection
Set selection73 = productDocument2.Selection

selection73.Clear

selection73.Add product80

selection73.Delete

Set documents1 = CATIA.Documents

Dim partDocument2 As PartDocument
Set partDocument2 = documents1.Open("D:\documents\Centrale Lyon\S8\PLM\insertion_vis\catalogue_vis_ecrou_rondelle\outils\plate_24.CATPart")

Set documents1 = CATIA.Documents

Dim partDocument3 As PartDocument
Set partDocument3 = documents1.Open("D:\documents\Centrale Lyon\S8\PLM\insertion_vis\catalogue_vis_ecrou_rondelle\outils\plate_7.CATPart")

Set documents1 = CATIA.Documents

Dim partDocument4 As PartDocument
Set partDocument4 = documents1.Open("D:\documents\Centrale Lyon\S8\PLM\insertion_vis\catalogue_vis_ecrou_rondelle\outils\plate_8.CATPart")

Set documents1 = CATIA.Documents

Dim partDocument5 As PartDocument
Set partDocument5 = documents1.Open("D:\documents\Centrale Lyon\S8\PLM\insertion_vis\catalogue_vis_ecrou_rondelle\outils\plate_10.CATPart")

Dim windows1 As Windows
Set windows1 = CATIA.Windows

Dim specsAndGeomWindow2 As SpecsAndGeomWindow
Set specsAndGeomWindow2 = windows1.Item("plate_7.CATPart")

specsAndGeomWindow2.Activate

Dim specsAndGeomWindow3 As SpecsAndGeomWindow
Set specsAndGeomWindow3 = windows1.Item("plate_8.CATPart")

specsAndGeomWindow3.Activate

Dim specsAndGeomWindow4 As SpecsAndGeomWindow
Set specsAndGeomWindow4 = windows1.Item("plate_10.CATPart")

specsAndGeomWindow4.Activate

Set documents1 = CATIA.Documents

Dim partDocument6 As PartDocument
Set partDocument6 = documents1.Open("D:\documents\Centrale Lyon\S8\PLM\insertion_vis\catalogue_vis_ecrou_rondelle\outils\plate_13.CATPart")

Set documents1 = CATIA.Documents

Dim partDocument7 As PartDocument
Set partDocument7 = documents1.Open("D:\documents\Centrale Lyon\S8\PLM\insertion_vis\catalogue_vis_ecrou_rondelle\outils\plate_16.CATPart")

Set documents1 = CATIA.Documents

Dim partDocument8 As PartDocument
Set partDocument8 = documents1.Open("D:\documents\Centrale Lyon\S8\PLM\insertion_vis\catalogue_vis_ecrou_rondelle\outils\plate_18.CATPart")

Dim specsAndGeomWindow5 As SpecsAndGeomWindow
Set specsAndGeomWindow5 = windows1.Item("plate_13.CATPart")

specsAndGeomWindow5.Activate

Dim specsAndGeomWindow6 As SpecsAndGeomWindow
Set specsAndGeomWindow6 = windows1.Item("plate_16.CATPart")

specsAndGeomWindow6.Activate

Dim specsAndGeomWindow7 As SpecsAndGeomWindow
Set specsAndGeomWindow7 = windows1.Item("plate_18.CATPart")

specsAndGeomWindow7.Activate

specsAndGeomWindow7.Close

Set partDocument8 = CATIA.ActiveDocument

partDocument8.Close

Dim viewer3D1 As Viewer3D
Set viewer3D1 = specsAndGeomWindow2.ActiveViewer

Dim viewpoint3D1 As Viewpoint3D
Set viewpoint3D1 = viewer3D1.Viewpoint3D

Dim product81 As Product
Set product81 = partDocument3.GetItem("plate_7 ")

product81.PartNumber = "plate_7"

Set partDocument3 = CATIA.ActiveDocument

partDocument3.Save

specsAndGeomWindow2.Close

Set partDocument3 = CATIA.ActiveDocument

partDocument3.Close

Dim product82 As Product
Set product82 = partDocument7.GetItem("plate_16 ")

product82.PartNumber = "plate_16"

Set partDocument7 = CATIA.ActiveDocument

partDocument7.Save

specsAndGeomWindow6.Close

Set partDocument7 = CATIA.ActiveDocument

partDocument7.Close

specsAndGeomWindow5.Close

Set partDocument6 = CATIA.ActiveDocument

partDocument6.Close

Dim product83 As Product
Set product83 = partDocument5.GetItem(" ")

product83.PartNumber = "plate_10"

Set partDocument5 = CATIA.ActiveDocument

partDocument5.Save

specsAndGeomWindow4.Close

Set partDocument5 = CATIA.ActiveDocument

partDocument5.Close

Dim product84 As Product
Set product84 = partDocument4.GetItem("plate_8 ")

product84.PartNumber = "plate_8"

Set partDocument4 = CATIA.ActiveDocument

partDocument4.Save

specsAndGeomWindow3.Close

Set partDocument4 = CATIA.ActiveDocument

partDocument4.Close

Dim product85 As Product
Set product85 = partDocument2.GetItem("plate_24 ")

product85.PartNumber = "plate_24"

Set partDocument2 = CATIA.ActiveDocument

partDocument2.Save

Dim specsAndGeomWindow8 As SpecsAndGeomWindow
Set specsAndGeomWindow8 = CATIA.ActiveWindow

specsAndGeomWindow8.Close

Set partDocument2 = CATIA.ActiveDocument

partDocument2.Close

Dim specsAndGeomWindow9 As SpecsAndGeomWindow
Set specsAndGeomWindow9 = CATIA.ActiveWindow

specsAndGeomWindow9.ActivateNext

Set productDocument2 = CATIA.ActiveDocument

Set product58 = productDocument2.Product

Set products35 = product58.Products

Set productDocument2 = CATIA.ActiveDocument

Dim selection74 As Selection
Set selection74 = productDocument2.Selection

selection74.Search "Name=LaVisserie*,all"

Dim long42 As Long
long42 = selection74.Count

Set productDocument2 = CATIA.ActiveDocument

Set product58 = productDocument2.Product

Set products35 = product58.Products

Set product60 = products35.Item("LaVisserie")

Dim bSTR342 As String
bSTR342 = product60.DescriptionRef

Set productDocument2 = CATIA.ActiveDocument

Set selection74 = productDocument2.Selection

selection74.Clear

Dim arrayOfVariantOfBSTR112(0)
arrayOfVariantOfBSTR112(0) = "Part"
Dim bSTR343 As String
Set selection74Variant = selection74
bSTR343 = selection74Variant.SelectElement2(arrayOfVariantOfBSTR112, "Sélectionner un élément de la visserie", False)

Dim selectedElement116 As SelectedElement
Set selectedElement116 = selection74.Item(1)

Set product63 = selectedElement116.LeafProduct

Set products37 = product63.Parent

Set product62 = products37.Parent

Dim bSTR344 As String
bSTR344 = product62.PartNumber

Dim selectedElement117 As SelectedElement
Set selectedElement117 = selection74.Item(1)

Set product63 = selectedElement117.LeafProduct

Set products37 = product63.Parent

Set product62 = products37.Parent

Set products37 = product62.Products

Set product63 = products37.Item(1)

Set product64 = products37.Item(2)

Dim bSTR345 As String
bSTR345 = product63.PartNumber

Dim bSTR346 As String
bSTR346 = product63.PartNumber

selection74.Clear

Set products37 = product62.Products

Set product63 = products37.Item(1)

Set product64 = products37.Item(2)

Dim bSTR347 As String
bSTR347 = product63.PartNumber

Set productDocument2 = CATIA.ActiveDocument

Set product58 = productDocument2.Product

Set products35 = product58.Products

Set productDocument2 = CATIA.ActiveDocument

Set product58 = productDocument2.Product

Set products35 = product58.Products

Set product60 = products35.Item("LaVisserie")

Set products36 = product60.Products

Dim product86 As Product
Set product86 = products36.AddNewProduct("setOutil")

Dim products47 As Products
Set products47 = product86.Products

Dim arrayOfVariantOfBSTR113(0)
arrayOfVariantOfBSTR113(0) = "D:\documents\Centrale Lyon\S8\PLM\insertion_vis\catalogue_vis_ecrou_rondelle\outils\plate_7.CATPart"
Set products47Variant = products47
products47Variant.AddComponentsFromFiles arrayOfVariantOfBSTR113, "All"

Set products47 = product86.Products

Dim product87 As Product
Set product87 = products47.Item("plate_7.1")

Dim publications33 As Publications
Set publications33 = product87.Publications

Dim publication72 As Publication
Set publication72 = publications33.Item("Axe")

Set publications33 = product87.Publications

Dim publication73 As Publication
Set publication73 = publications33.Item("Face_inf")

Dim arrayOfVariantOfBSTR114(0)
arrayOfVariantOfBSTR114(0) = "D:\documents\Centrale Lyon\S8\PLM\insertion_vis\catalogue_vis_ecrou_rondelle\outils\douille_7.CATPart"
Set products47Variant = products47
products47Variant.AddComponentsFromFiles arrayOfVariantOfBSTR114, "All"

Set products47 = product86.Products

Dim product88 As Product
Set product88 = products47.Item("douille_7.1")

Dim publications34 As Publications
Set publications34 = product88.Publications

Dim publication74 As Publication
Set publication74 = publications34.Item("Axe")

Set publications34 = product88.Publications

Dim publication75 As Publication
Set publication75 = publications34.Item("Face_inf")

Set publications24 = product63.Publications

Set publication53 = publications24.Item("AxeVis")

Set publications24 = product63.Publications

Set publication52 = publications24.Item("FaceRondelle")

Set publications25 = product64.Publications

Set publication54 = publications25.Item("FaceRondelle")

Set productDocument2 = CATIA.ActiveDocument

Set selection74 = productDocument2.Selection

selection74.Clear

Dim bSTR348 As String
bSTR348 = product86.Name

Set products36 = product60.Products

Set product86 = products36.Item("setOutil.6")

selection74.Add product86

CATIA.StartCommand "Flexible/rigide"

selection74.Clear

Set constraints3 = product58.Connections("CATIAConstraints")

Dim reference45 As Reference
' No resolution found for the object reference45...

Dim constraint45 As Constraint
Set constraint45 = constraints3.AddBiEltCst(catCstTypeOn, reference45, reference31)

Dim reference46 As Reference
' No resolution found for the object reference46...

Dim constraint46 As Constraint
Set constraint46 = constraints3.AddBiEltCst(catCstTypeOn, reference46, reference31)

Set productDocument2 = CATIA.ActiveDocument

Set product58 = productDocument2.Product

product58.Update

Set productDocument2 = CATIA.ActiveDocument

Dim selection75 As Selection
Set selection75 = productDocument2.Selection

selection75.Clear

selection75.Add constraint45

selection75.Add constraint46

selection75.Add product86

selection75.Delete

Set productDocument2 = CATIA.ActiveDocument

Set product58 = productDocument2.Product

Set products35 = product58.Products

Set productDocument2 = CATIA.ActiveDocument

Dim selection76 As Selection
Set selection76 = productDocument2.Selection

selection76.Search "Name=LaVisserie*,all"

Dim long43 As Long
long43 = selection76.Count

Set productDocument2 = CATIA.ActiveDocument

Set product58 = productDocument2.Product

Set products35 = product58.Products

Set product60 = products35.Item("LaVisserie")

Dim bSTR349 As String
bSTR349 = product60.DescriptionRef

Set productDocument2 = CATIA.ActiveDocument

Set selection76 = productDocument2.Selection

selection76.Clear

Dim arrayOfVariantOfBSTR115(0)
arrayOfVariantOfBSTR115(0) = "Part"
Dim bSTR350 As String
Set selection76Variant = selection76
bSTR350 = selection76Variant.SelectElement2(arrayOfVariantOfBSTR115, "Sélectionner un élément de la visserie", False)

Dim selectedElement118 As SelectedElement
Set selectedElement118 = selection76.Item(1)

Set product63 = selectedElement118.LeafProduct

Set products37 = product63.Parent

Set product62 = products37.Parent

Dim bSTR351 As String
bSTR351 = product62.PartNumber

Dim selectedElement119 As SelectedElement
Set selectedElement119 = selection76.Item(1)

Set product63 = selectedElement119.LeafProduct

Set products37 = product63.Parent

Set product62 = products37.Parent

Set products37 = product62.Products

Set product63 = products37.Item(1)

Set product64 = products37.Item(2)

Dim bSTR352 As String
bSTR352 = product63.PartNumber

Dim bSTR353 As String
bSTR353 = product63.PartNumber

selection76.Clear

Set products37 = product62.Products

Set product63 = products37.Item(1)

Set product64 = products37.Item(2)

Dim bSTR354 As String
bSTR354 = product63.PartNumber

Set productDocument2 = CATIA.ActiveDocument

Set product58 = productDocument2.Product

Set products35 = product58.Products

Set productDocument2 = CATIA.ActiveDocument

Set product58 = productDocument2.Product

Set products35 = product58.Products

Set product60 = products35.Item("LaVisserie")

Set products36 = product60.Products

Dim product89 As Product
Set product89 = products36.AddNewProduct("setOutil")

Dim products48 As Products
Set products48 = product89.Products

Dim arrayOfVariantOfBSTR116(0)
arrayOfVariantOfBSTR116(0) = "D:\documents\Centrale Lyon\S8\PLM\insertion_vis\catalogue_vis_ecrou_rondelle\outils\douille_7.CATPart"
Set products48Variant = products48
products48Variant.AddComponentsFromFiles arrayOfVariantOfBSTR116, "All"

Set products48 = product89.Products

Dim product90 As Product
Set product90 = products48.Item("douille_7.1")

Dim publications35 As Publications
Set publications35 = product90.Publications

Dim publication76 As Publication
Set publication76 = publications35.Item("Axe")

Set publications35 = product90.Publications

Dim publication77 As Publication
Set publication77 = publications35.Item("Face_inf")

Dim arrayOfVariantOfBSTR117(0)
arrayOfVariantOfBSTR117(0) = "D:\documents\Centrale Lyon\S8\PLM\insertion_vis\catalogue_vis_ecrou_rondelle\outils\douille_7.CATPart"
Set products48Variant = products48
products48Variant.AddComponentsFromFiles arrayOfVariantOfBSTR117, "All"

Set products48 = product89.Products

Set product90 = products48.Item("douille_7.1")

Set publications35 = product90.Publications

Set publication76 = publications35.Item("Axe")

Set publications35 = product90.Publications

Set publication77 = publications35.Item("Face_inf")

Set publications24 = product63.Publications

Set publication53 = publications24.Item("AxeVis")

Set publications24 = product63.Publications

Set publication52 = publications24.Item("FaceRondelle")

Set publications25 = product64.Publications

Set publication54 = publications25.Item("FaceRondelle")

Set productDocument2 = CATIA.ActiveDocument

Set selection76 = productDocument2.Selection

selection76.Clear

Dim bSTR355 As String
bSTR355 = product89.Name

Set products36 = product60.Products

Set product89 = products36.Item("setOutil.7")

selection76.Add product89

CATIA.StartCommand "Flexible/rigide"

selection76.Clear

Set constraints3 = product58.Connections("CATIAConstraints")

Dim reference47 As Reference
' No resolution found for the object reference47...

Dim constraint47 As Constraint
Set constraint47 = constraints3.AddBiEltCst(catCstTypeOn, reference47, reference31)

Dim constraint48 As Constraint
Set constraint48 = constraints3.AddBiEltCst(catCstTypeOn, reference47, reference31)

Set productDocument2 = CATIA.ActiveDocument

Set product58 = productDocument2.Product

product58.Update

specsAndGeomWindow9.Close

Set productDocument2 = CATIA.ActiveDocument

productDocument2.Close

CATIA.Quit

End Sub
